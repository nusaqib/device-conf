ENVIROMUX2D DEFINITIONS ::= BEGIN
IMPORTS
   NOTIFICATION-GROUP, OBJECT-GROUP             FROM SNMPv2-CONF
   MODULE-IDENTITY, OBJECT-TYPE, 
   NOTIFICATION-TYPE, enterprises,
   Integer32                                    FROM  SNMPv2-SMI
   DisplayString                                FROM  SNMPv2-TC;
      
enviromux2D MODULE-IDENTITY
     LAST-UPDATED "202406031000Z"
     ORGANIZATION "Network Technologies Inc."
     CONTACT-INFO 
         "Network Technologies Inc.
         
          Postal: 1275 Danner Dr,
                  Aurora, OH 442022
                  US
                 
          Tel: 330-562-7070
          Fax: 330-562-1999
             
          WEB: www.networktechinc.com"
	 
     DESCRIPTION 
         "ENVIROMUX-2D MIB file." 
     REVISION     "202406031000Z"
         DESCRIPTION "Rev. 1.23 - Added new integer value for IP Sensor Rebooter Types, Ping Target and OutRelay"
     REVISION     "202302131400Z"
         DESCRIPTION "Rev. 1.22 - Added separate integer value OID and unit OID for all external sensors"
     REVISION     "201911261400Z"
         DESCRIPTION "Rev. 1.21 - Added separate section to include all external sensors"
     REVISION     "201908151400Z"
         DESCRIPTION "Rev. 1.20 - Defined events traps and changes to events description"   
     REVISION     "201904251400Z"
         DESCRIPTION "Rev. 1.19 - Defined remote digital input and remote relay traps"
     REVISION     "201810011600Z" 
         DESCRIPTION  "Rev. 1.18 - Added ALDS Sensor and fixed MIB file errors"  
     REVISION     "201804141500Z" 
         DESCRIPTION  "Rev. 1.16 - Enable network security"  
     REVISION     "201803051000Z" 
         DESCRIPTION  "Rev. 1.15 - software reset/network config"  
     REVISION     "201712101600Z" 
         DESCRIPTION  "Rev. 1.14 - add writable sensor threshold"    
     REVISION     "201711281600Z" 
         DESCRIPTION  "Rev. 1.13 - add firmware version; add writable message registers"    
     REVISION     "201708081500Z" 
         DESCRIPTION  "Rev. 1.12 - Change alert/event status registers to be read-write"    
     REVISION     "201611201400Z" 
         DESCRIPTION  "Rev. 1.11 - Added type definitions for ACLM3 sensors"    
     REVISION     "201609031400Z" 
         DESCRIPTION  "Rev. 1.10 - Added definitions for warning thresholds"    
     REVISION     "201603041400Z" 
         DESCRIPTION  "Rev. 1.09 - Added Auxiliary 2 sensors"    
     REVISION     "201510141400Z" 
         DESCRIPTION  "Rev. 1.08 - Added ACDC sensors"    
     REVISION     "201411171400Z" 
         DESCRIPTION  "Rev. 1.07 - Added IP sensors"    
     REVISION     "201403171400Z" 
         DESCRIPTION  "Rev. 1.06 - Fixed compile errors or warnings"    
     REVISION     "201312041400Z" 
         DESCRIPTION  "Rev. 1.05 - Fixed attributes for OIDs, made relays writable"    
     REVISION     "201305091400Z" 
         DESCRIPTION  "Rev. 1.04 - Changes for Tac sensor on Digital input 1"            
    REVISION     "201304251400Z" 
         DESCRIPTION  "Rev. 1.03 - Changes for high accuracy temperature humidity sensor"                                
    REVISION     "201302040000Z" 
         DESCRIPTION  "Rev. 1.02 - Changes for REV C pcb;Added Smoke Detectors"                                
    REVISION     "201212121400Z" 
         DESCRIPTION  "Rev. 1.01 - added remote inputs and remote relays;Added Events and Smart Alerts"
    REVISION     "201211200000Z" 
         DESCRIPTION  "Rev. 1.00 - Initial version"
     ::= { hardware 9 }

-- the root of the subtree for Network Technologies Inc
nti		        OBJECT IDENTIFIER ::= { enterprises 3699 }

-- subtree for products
products		        OBJECT IDENTIFIER ::= { nti 1 }
hardware		        OBJECT IDENTIFIER ::= { products 1 }
software		        OBJECT IDENTIFIER ::= { products 2 }
otherProduct            OBJECT IDENTIFIER ::= { hardware 200 }

-- ipdus2 subtree
masterUnit	            OBJECT IDENTIFIER ::= { enviromux2D 1 }
envTraps                OBJECT IDENTIFIER ::= { enviromux2D 100 }
hostSystem              OBJECT IDENTIFIER ::= { masterUnit 1 }
users                   OBJECT IDENTIFIER ::= { masterUnit 2 }
intSensors		        OBJECT IDENTIFIER ::= { masterUnit 3 }
auxSensors              OBJECT IDENTIFIER ::= { masterUnit 4 }
extSensors		        OBJECT IDENTIFIER ::= { masterUnit 5 }
digInputs               OBJECT IDENTIFIER ::= { masterUnit 6 }
ipDevices 		        OBJECT IDENTIFIER ::= { masterUnit 7 }
outRelays 		        OBJECT IDENTIFIER ::= { masterUnit 8 }
pwrSupplies 	        OBJECT IDENTIFIER ::= { masterUnit 9 }
events                  OBJECT IDENTIFIER ::= { masterUnit 10 }
smartAlerts             OBJECT IDENTIFIER ::= { masterUnit 11 }
remoteInputs            OBJECT IDENTIFIER ::= { masterUnit 12 }
remoteRelays            OBJECT IDENTIFIER ::= { masterUnit 13 }
smokeDetectors          OBJECT IDENTIFIER ::= { masterUnit 14 }
tacSensors              OBJECT IDENTIFIER ::= { masterUnit 15 }
ipSensors               OBJECT IDENTIFIER ::= { masterUnit 16 }
aux2Sensors             OBJECT IDENTIFIER ::= { masterUnit 17 }
msgRegisters            OBJECT IDENTIFIER ::= { masterUnit 18 }
netConfRegisters        OBJECT IDENTIFIER ::= { masterUnit 20 }
allExternalSensors      OBJECT IDENTIFIER ::= { masterUnit 21 }
envGroups               OBJECT IDENTIFIER ::= { masterUnit 200 }

-- groups

sysGroup                OBJECT-GROUP
    OBJECTS             { sysTime, sysEnterpriseName, sysEnterpriseLocation, sysEnterpriseBranch, sysEnterpriseContact, sysEnterpriseRack, sysEnterpriseContact, sysEnterprisePhone, firmwareVersion, deviceModel, sysReset, devSerialNum, devHardwareRev, devManufacturer}
    STATUS              current
    DESCRIPTION         "System parameters group"
    ::= {envGroups 1}

intSensorsGrp           OBJECT-GROUP
    OBJECTS             { intSensorIndex, intSensorType, intSensorDescription, intSensorGroupNb, intSensorGroup,
                        intSensorValue, intSensorUnit, intSensorUnitName, intSensorStatus, intSensorMinThreshold, intSensorMaxThreshold }
    STATUS              current
    DESCRIPTION         "External sensors group"
    ::= {envGroups 2}

extSensorsGrp           OBJECT-GROUP
    OBJECTS             { extSensorIndex, extSensorType, extSensorDescription, extSensorConnector, extSensorGroupNb, extSensorGroup,
                        extSensorValue, extSensorUnit, extSensorUnitName, extSensorStatus, extSensorMinThreshold, extSensorMaxThreshold }
    STATUS              current
    DESCRIPTION         "External sensors group"
    ::= {envGroups 3}

digInputsGrp            OBJECT-GROUP
    OBJECTS             { digInputIndex, digInputType, digInputDescription, digInputConnector, digInputGroupNb, digInputGroup,
                        digInputValue, digInputStatus, digInputNormalValue }
    STATUS              current
    DESCRIPTION         "Dry contacts group"
    ::= {envGroups 5}

ipDeviceGrp            OBJECT-GROUP
    OBJECTS             { ipDeviceIndex, ipDeviceAddress, ipDeviceDescription, ipDeviceGroupNb, ipDeviceGroup, ipDeviceTimeout, ipDeviceRetries, 
                        ipDeviceValue, ipDeviceStatus }
    STATUS              current
    DESCRIPTION         "IP devices group"
    ::= {envGroups 6}

outRelaysGrp           OBJECT-GROUP
    OBJECTS             { outRelayIndex, outRelayDescription, outRelayStatus }
    STATUS              current
    DESCRIPTION         "Dry contacts group"
    ::= {envGroups 7}

miscTrapFields          OBJECT-GROUP
    OBJECTS             { envTrapDescription, envTrapValue }
    STATUS              current
    DESCRIPTION         "General Information Traps"
    ::= {envGroups 8}

intSensorTrapGrp        NOTIFICATION-GROUP
    NOTIFICATIONS       { intSensor1Trap }
    STATUS              current
    DESCRIPTION         "Internal Sensors Traps Group"
    ::= {envGroups 9}
    
extSensorTrapGrp        NOTIFICATION-GROUP
    NOTIFICATIONS       { extSensor1Trap,  extSensor2Trap,  extSensor3Trap,  extSensor4Trap }
    STATUS              current
    DESCRIPTION         "External Sensors Traps Group"
    ::= {envGroups 10}
    
digInputTrapGrp        NOTIFICATION-GROUP
    NOTIFICATIONS       { digInput1Trap, digInput2Trap, digInput3Trap, digInput4Trap, digInput5Trap }
    STATUS              current
    DESCRIPTION         "External Sensors Traps Group"
    ::= {envGroups 12}

ipDeviceTrapGrp        NOTIFICATION-GROUP
    NOTIFICATIONS       { ipDevice1Trap,  ipDevice2Trap,  ipDevice3Trap,  ipDevice4Trap,  ipDevice5Trap,  ipDevice6Trap,  ipDevice7Trap,  ipDevice8Trap, 
                          ipDevice9Trap,  ipDevice10Trap, ipDevice11Trap, ipDevice12Trap, ipDevice13Trap, ipDevice14Trap, ipDevice15Trap, ipDevice16Trap, 
                          ipDevice17Trap, ipDevice18Trap, ipDevice19Trap, ipDevice20Trap, ipDevice21Trap, ipDevice22Trap, ipDevice23Trap, ipDevice24Trap, 
                          ipDevice25Trap, ipDevice26Trap, ipDevice27Trap, ipDevice28Trap, ipDevice29Trap, ipDevice30Trap, ipDevice31Trap, ipDevice32Trap, 
                          ipDevice33Trap, ipDevice34Trap, ipDevice35Trap, ipDevice36Trap, ipDevice37Trap, ipDevice38Trap, ipDevice39Trap, ipDevice40Trap, 
                          ipDevice41Trap, ipDevice42Trap, ipDevice43Trap, ipDevice44Trap, ipDevice45Trap, ipDevice46Trap, ipDevice47Trap, ipDevice48Trap, 
                          ipDevice49Trap, ipDevice50Trap, ipDevice51Trap, ipDevice52Trap, ipDevice53Trap, ipDevice54Trap, ipDevice55Trap, ipDevice56Trap, 
                          ipDevice57Trap, ipDevice58Trap, ipDevice59Trap, ipDevice60Trap, ipDevice61Trap, ipDevice62Trap, ipDevice63Trap, ipDevice64Trap }
    STATUS              current
    DESCRIPTION         "IP Device Traps Group"
    ::= {envGroups 13}

miscNotificationGrp    NOTIFICATION-GROUP
    NOTIFICATIONS       { evLogFileTrap, dataLogFileTrap, remoteDataLogFileTrap}
    STATUS              current
    DESCRIPTION         "Other Traps Group"
    ::= {envGroups 14}

pwrSuppliesGrp         OBJECT-GROUP     
    OBJECTS             { pwrSupplyIndex, pwrSupplyStatus }
    STATUS              current
    DESCRIPTION         "Power supplies group"
    ::= {envGroups 15}

msgRegistersGrp         OBJECT-GROUP
    OBJECTS             { msgRegistersIndex, msgRegistersDescription, msgRegistersStatus }
    STATUS              current
    DESCRIPTION         "message registers group"
    ::= {envGroups 16}

netConfRegistersGrp     OBJECT-GROUP
    OBJECTS             { netConfIPv4Mode, netConfIPv4Addr, netConfIPv4Mask, netConfIPv4Gateway, netConfPreDNS, netConfAltDNS, netConfDNSTimeout, 
						  netConfIPv6Mode, netConfIPv6Addr, netConfIPv6Gateway, netConfEnable6to4Tunnel, netConfLocalIPAddr, netConfRemoteIPv4Addr, netConfVlanEnabled, netConfVlanID, netConfSave, netConfEnableSecurity}
    STATUS              current
    DESCRIPTION         "network configure registers group"
    ::= {envGroups 18}


remoteRelaysGrp           OBJECT-GROUP
    OBJECTS             { remoteRelayIndex, remoteRelayDescription, remoteRelayStatus }
    STATUS              current
    DESCRIPTION         "Remote Output Relay group"
    ::= {envGroups 19}

remoteInputsGrp            OBJECT-GROUP
    OBJECTS             { remoteInputIndex, remoteInputType, remoteInputDescription, remoteInputConnector, remoteInputGroupNb, remoteInputGroup,
                        remoteInputValue, remoteInputStatus, remoteInputNormalValue }
    STATUS              current
    DESCRIPTION         "Dry Contact group"
    ::= {envGroups 20}

remoteInputTrapGrp        NOTIFICATION-GROUP
    NOTIFICATIONS       {   remoteInput1Trap,   remoteInput2Trap,   remoteInput3Trap,   remoteInput4Trap,   remoteInput5Trap, remoteInput6Trap, remoteInput7Trap, remoteInput8Trap, 
                            remoteInput9Trap,   remoteInput10Trap,  remoteInput11Trap,  remoteInput12Trap,  remoteInput13Trap,  remoteInput14Trap,  remoteInput15Trap, 
                            remoteInput16Trap}
    STATUS              current
    DESCRIPTION         "Dry Contact group"
    ::= {envGroups 21}

remoteRelayTrapGrp          NOTIFICATION-GROUP
    NOTIFICATIONS       {   remoteRelay1Trap, remoteRelay2Trap, remoteRelay3Trap, remoteRelay4Trap, remoteRelay5Trap, remoteRelay6Trap, remoteRelay7Trap, remoteRelay8Trap, 
                            remoteRelay9Trap, remoteRelay10Trap, remoteRelay11Trap, remoteRelay12Trap, remoteRelay13Trap, remoteRelay14Trap, remoteRelay15Trap, 
                            remoteRelay16Trap}
    STATUS              current
    DESCRIPTION         "Remote Output Relay group"
    ::= {envGroups 22}

eventTrapGrp          NOTIFICATION-GROUP
    NOTIFICATIONS       {   event1Trap, event2Trap, event3Trap, event4Trap, event5Trap, event6Trap, event7Trap, event8Trap, 
                            event9Trap, event10Trap, event11Trap, event12Trap, event13Trap, event14Trap, event15Trap, 
                            event16Trap, event17Trap, event18Trap, event19Trap, event20Trap, event21Trap, event22Trap, event23Trap, event24Trap, 
                            event25Trap, event26Trap, event27Trap, event28Trap, event29Trap, event30Trap, event31Trap, 
                            event32Trap}
    STATUS              current
    DESCRIPTION         "event group"
    ::= {envGroups 23}
	
-- hostSystem subtree

sysTime					OBJECT-TYPE
	SYNTAX				DisplayString
	MAX-ACCESS			read-only
	STATUS				current
	DESCRIPTION		    "System time"
	::= { hostSystem 1 }

sysEnterpriseName		OBJECT-TYPE
	SYNTAX				DisplayString
	MAX-ACCESS  		read-only
	STATUS				current
	DESCRIPTION		    "Enterprise Name"
	::= { hostSystem 2 }

sysEnterpriseLocation	OBJECT-TYPE
	SYNTAX				DisplayString
	MAX-ACCESS  		read-only
	STATUS				current
	DESCRIPTION		    "Enterprise Location"
	::= { hostSystem 3 }

sysEnterpriseBranch 	OBJECT-TYPE
	SYNTAX				DisplayString
	MAX-ACCESS  		read-only
	STATUS				current
	DESCRIPTION		    "Enterprise Branch"
	::= { hostSystem 4 }

sysEnterpriseRack	OBJECT-TYPE
	SYNTAX				DisplayString
	MAX-ACCESS  		read-only
	STATUS				current
	DESCRIPTION		    "Enterprise Rack"
	::= { hostSystem 5 }

sysEnterpriseContact	OBJECT-TYPE
	SYNTAX				DisplayString
	MAX-ACCESS  		read-only
	STATUS				current
	DESCRIPTION		    "Enterprise Contact"
	::= { hostSystem 6 }

sysEnterprisePhone  	OBJECT-TYPE
	SYNTAX				DisplayString
	MAX-ACCESS  		read-only
	STATUS				current
	DESCRIPTION		    "Enterprise Phone"
	::= { hostSystem 7 }

firmwareVersion  		OBJECT-TYPE
	SYNTAX				DisplayString
	MAX-ACCESS  		read-only
	STATUS				current
	DESCRIPTION		    "Firmware Version"
	::= { hostSystem 8 }

deviceModel  			OBJECT-TYPE
	SYNTAX				DisplayString
	MAX-ACCESS  		read-only
	STATUS				current
	DESCRIPTION		    "Device Model"
	::= { hostSystem 9 }

sysReset				OBJECT-TYPE
	SYNTAX				INTEGER {normal(0), reboot(1)}
	MAX-ACCESS			read-write
	STATUS				current
	DESCRIPTION		    "Initiates system reboot. Normal value: 0, set 1 to reboot"
	::= { hostSystem 10 }

devSerialNum 			OBJECT-TYPE
	SYNTAX				DisplayString		
	MAX-ACCESS			read-only
	STATUS				current
	DESCRIPTION		    "Serial Number"
	::= { hostSystem 11 }

devHardwareRev			OBJECT-TYPE
	SYNTAX				DisplayString		
	MAX-ACCESS			read-only
	STATUS				current
	DESCRIPTION		    "Hardware Revision"
	::= { hostSystem 12 }

devManufacturer			OBJECT-TYPE
	SYNTAX				DisplayString		
	MAX-ACCESS			read-only
	STATUS				current
	DESCRIPTION		    "Device Manufacturer"
	::= { hostSystem 13 }

-- internal sensors description

intSensorTable			OBJECT-TYPE
	SYNTAX	            SEQUENCE OF	IntSensorEntry
	MAX-ACCESS          not-accessible
	STATUS	            current
	DESCRIPTION         "Table of internal Sensors entries"
	::= { intSensors 1 }

intSensorEntry     		OBJECT-TYPE
    SYNTAX              IntSensorEntry
	MAX-ACCESS          not-accessible
	STATUS	            current
	DESCRIPTION         "An internal sensor entry"
	INDEX               { intSensorIndex }
	::= { intSensorTable 1 }

IntSensorEntry ::= 
	SEQUENCE {
		intSensorIndex
			Integer32,
		intSensorType
			INTEGER,
		intSensorDescription
			DisplayString,
		intSensorGroupNb
			Integer32,
		intSensorGroup
			DisplayString,
        intSensorValue
            INTEGER,
		intSensorUnit
			Integer32,
		intSensorUnitName
			DisplayString,
		intSensorStatus
			INTEGER,
		intSensorMinThreshold
			Integer32,
		intSensorMaxThreshold
			Integer32,
		intSensorMinWarnThreshold
			Integer32,
		intSensorMaxWarnThreshold
			Integer32
	}

intSensorIndex			OBJECT-TYPE
	SYNTAX				Integer32 (0..10000)
	MAX-ACCESS			accessible-for-notify
	STATUS				current
	DESCRIPTION	        "The index of the internal sensor entry 1..3"
	::= { intSensorEntry 1 }

intSensorType		    OBJECT-TYPE
	SYNTAX				INTEGER {  undefined(0), temperature(1), humidity(2), power(3), lowVoltage(4), current(5), aclmvVoltage(6), aclmpVoltage(7), aclmpPower(8),water(9), smoke(10), vibration(11), motion(12), glass(13), door(14), keypad(15), panicButton(16), keyStation(17), digInput(18), light(22), rmsVoltage(41), rmsCurrent(42), activePower(43), reactivePower(44), tempHum(513), custom(32767), temperatureCombo(32769), humidityCombo(32770), tempHum2(540)  }
	MAX-ACCESS  		read-only
	STATUS				current
	DESCRIPTION	        "Sensor Type"
	::= { intSensorEntry 2 }

intSensorDescription    OBJECT-TYPE
	SYNTAX				DisplayString
	MAX-ACCESS  		read-only
	STATUS				current
	DESCRIPTION	        "Sensor Description"
	::= { intSensorEntry 3 }
    
intSensorGroupNb        OBJECT-TYPE
	SYNTAX				Integer32 (1..8)
	MAX-ACCESS  		read-only
	STATUS				current
	DESCRIPTION	        "Sensor's Group"
	::= { intSensorEntry 4 }
    
intSensorGroup          OBJECT-TYPE
	SYNTAX				DisplayString
	MAX-ACCESS  		read-only
	STATUS				current
	DESCRIPTION	        "Sensor's Group Name"
	::= { intSensorEntry 5 }
    
intSensorValue			OBJECT-TYPE
	SYNTAX				INTEGER { closed(0), open(1) }
	MAX-ACCESS			read-only
	STATUS				current
	DESCRIPTION	        "The value of the internal sensor reading. For temperature, voltage, current or low voltage,  it is presented in tenths of degrees/volts"
	::= { intSensorEntry 6 }
	
intSensorUnit			OBJECT-TYPE
	SYNTAX				Integer32 (0..1)
	MAX-ACCESS			read-only
	STATUS				current
	DESCRIPTION	        "The measuremnet unit for this sensor in numeric format. It is important only for temperature"
	::= { intSensorEntry 7 }
	
intSensorUnitName   	OBJECT-TYPE
	SYNTAX				DisplayString
	MAX-ACCESS			read-only
	STATUS				current
	DESCRIPTION	        "The measuremnet unit for this sensor in readable format"
	::= { intSensorEntry 8 }
	
intSensorStatus			OBJECT-TYPE
	SYNTAX				INTEGER {notconnected(0), normal(1), prealert(2), alert(3), acknowledged(4), dismissed(5), disconnected(6) }
	MAX-ACCESS			read-write
	STATUS				current
	DESCRIPTION	        "The status of the sensor"
	::= { intSensorEntry 9 }
	
intSensorMinThreshold	OBJECT-TYPE
	SYNTAX				Integer32 (0..1000)
	MAX-ACCESS			read-write
	STATUS				current
	DESCRIPTION	        "The value of the sensor lower threshold"
	::= { intSensorEntry 10 }
	
intSensorMaxThreshold	OBJECT-TYPE
	SYNTAX				Integer32 (0..1000)
	MAX-ACCESS			read-write
	STATUS				current
	DESCRIPTION	        "The value of the sensor upper threshold"
	::= { intSensorEntry 11 }
	
intSensorMinWarnThreshold	OBJECT-TYPE
	SYNTAX				Integer32 (0..1000)
	MAX-ACCESS			read-write
	STATUS				current
	DESCRIPTION	        "The value of the sensor lower warning threshold"
	::= { intSensorEntry 12 }
	
intSensorMaxWarnThreshold	OBJECT-TYPE
	SYNTAX				Integer32 (0..1000)
	MAX-ACCESS			read-write
	STATUS				current
	DESCRIPTION	        "The value of the sensor upper warning threshold"
	::= { intSensorEntry 13 }
	
-- external auxiliary sensors description

auxSensorTable		OBJECT-TYPE
	SYNTAX	            SEQUENCE OF	AuxSensorEntry
	MAX-ACCESS          not-accessible
	STATUS	            current
	DESCRIPTION         "Table of auxiliary sensors entries"
	::= { auxSensors 1 }

auxSensorEntry		OBJECT-TYPE
    SYNTAX              AuxSensorEntry
	MAX-ACCESS          not-accessible
	STATUS	            current
	DESCRIPTION         "An auxiliary sensor entry"
	INDEX               { auxSensorIndex }
	::= { auxSensorTable 1 }

AuxSensorEntry ::= 
	SEQUENCE {
		auxSensorIndex
			Integer32,
		auxSensorType
			INTEGER,
		auxSensorDescription
			DisplayString,
		auxSensorConnector
			Integer32,
		auxSensorGroupNb
			Integer32,
		auxSensorGroup
			DisplayString,
        auxSensorValue
            INTEGER,
		auxSensorUnit
			Integer32,
		auxSensorUnitName
			DisplayString,
		auxSensorStatus
			INTEGER,
		auxSensorMinThreshold
			Integer32,
		auxSensorMaxThreshold
			Integer32,
		auxSensorMinWarnThreshold
			Integer32,
		auxSensorMaxWarnThreshold
			Integer32
	}

auxSensorIndex			OBJECT-TYPE
	SYNTAX				Integer32 (0..10000)
	MAX-ACCESS			accessible-for-notify
	STATUS				current
	DESCRIPTION	        "The index of the auxiliary sensor entry 1..2"
	::= { auxSensorEntry 1 }

auxSensorType		    OBJECT-TYPE
	SYNTAX				INTEGER {  undefined(0), dewPoint(24), frequency(35), acVoltage(36), acCurrent(37), dcVoltage(38), dcCurrent(39), rmsVoltage(41), rmsCurrent(42), activePower(43), reactivePower(44) , aldsTotalLength(47) }
	MAX-ACCESS  		read-only
	STATUS				current
	DESCRIPTION	        "Auxiliary Sensor Type"
	::= { auxSensorEntry 2 }

auxSensorDescription    OBJECT-TYPE
	SYNTAX				DisplayString
	MAX-ACCESS  		read-only
	STATUS				current
	DESCRIPTION	        "Auxiliary Sensor Description"
	::= { auxSensorEntry 3 }
    
auxSensorConnector      OBJECT-TYPE
	SYNTAX				Integer32 (1..16)
	MAX-ACCESS  		read-only
	STATUS				current
	DESCRIPTION	        "Connector where the auxiliary sensor is attached"
	::= { auxSensorEntry 4 }
    
auxSensorGroupNb        OBJECT-TYPE
	SYNTAX				Integer32 (1..8)
	MAX-ACCESS  		read-only
	STATUS				current
	DESCRIPTION	        "Auxiliary Sensor's Group"
	::= { auxSensorEntry 5 }
    
auxSensorGroup          OBJECT-TYPE
	SYNTAX				DisplayString
	MAX-ACCESS  		read-only
	STATUS				current
	DESCRIPTION	        "Auxiliary Sensor's Group Name"
	::= { auxSensorEntry 6 }
    
auxSensorValue			OBJECT-TYPE
	SYNTAX				INTEGER
	MAX-ACCESS			read-only
	STATUS				current
	DESCRIPTION	        "The value of the auxiliary sensor reading. It is presented in tenths of degrees"
	::= { auxSensorEntry 7 }
	
auxSensorUnit			OBJECT-TYPE
	SYNTAX				Integer32 (0..1)
	MAX-ACCESS			read-only
	STATUS				current
	DESCRIPTION	        "The measuremnet unit for this sensor. Can be Celsius or Fahrenheit"
	::= { auxSensorEntry 8 }
	
auxSensorUnitName   	OBJECT-TYPE
	SYNTAX				DisplayString
	MAX-ACCESS			read-only
	STATUS				current
	DESCRIPTION	        "The measuremnet unit for this sensor in readable format"
	::= { auxSensorEntry 9 }
	
auxSensorStatus			OBJECT-TYPE
	SYNTAX				INTEGER {notconnected(0), normal(1), prealert(2), alert(3), acknowledged(4), dismissed(5), disconnected(6), notApplicable(11) }
	MAX-ACCESS			read-write
	STATUS				current
	DESCRIPTION	        "The status of the auxiliary sensor"
	::= { auxSensorEntry 10 }
	
auxSensorMinThreshold	OBJECT-TYPE
	SYNTAX				Integer32 (0..1000)
	MAX-ACCESS			read-write
	STATUS				current
	DESCRIPTION	        "The value of the sensor lower threshold"
	::= { auxSensorEntry 11 }
	
auxSensorMaxThreshold	OBJECT-TYPE
	SYNTAX				Integer32 (0..1000)
	MAX-ACCESS			read-write
	STATUS				current
	DESCRIPTION	        "The value of the sensor upper threshold"
	::= { auxSensorEntry 12 }
	
auxSensorMinWarnThreshold	OBJECT-TYPE
	SYNTAX				Integer32 (0..1000)
	MAX-ACCESS			read-write
	STATUS				current
	DESCRIPTION	        "The value of the sensor lower warning threshold"
	::= { auxSensorEntry 13 }
	
auxSensorMaxWarnThreshold	OBJECT-TYPE
	SYNTAX				Integer32 (0..1000)
	MAX-ACCESS			read-write
	STATUS				current
	DESCRIPTION	        "The value of the sensor upper warning threshold"
	::= { auxSensorEntry 14 }
	

-- external auxiliary 2 sensors description

aux2SensorTable		OBJECT-TYPE
	SYNTAX	            SEQUENCE OF	Aux2SensorEntry
	MAX-ACCESS          not-accessible
	STATUS	            current
	DESCRIPTION         "Table of auxiliary sensors entries"
	::= { aux2Sensors 1 }

aux2SensorEntry		OBJECT-TYPE
    SYNTAX              Aux2SensorEntry
	MAX-ACCESS          not-accessible
	STATUS	            current
	DESCRIPTION         "An auxiliary 2 sensor entry"
	INDEX               { aux2SensorIndex }
	::= { aux2SensorTable 1 }

Aux2SensorEntry ::= 
	SEQUENCE {
		aux2SensorIndex
			Integer32,
		aux2SensorType
			INTEGER,
		aux2SensorDescription
			DisplayString,
		aux2SensorConnector
			Integer32,
		aux2SensorGroupNb
			Integer32,
		aux2SensorGroup
			DisplayString,
        aux2SensorValue
            INTEGER,
		aux2SensorUnit
			Integer32,
		aux2SensorUnitName
			DisplayString,
		aux2SensorStatus
			INTEGER,
		aux2SensorMinThreshold
			Integer32,
		aux2SensorMaxThreshold
			Integer32,
		aux2SensorMinWarnThreshold
			Integer32,
		aux2SensorMaxWarnThreshold
			Integer32
	}

aux2SensorIndex			OBJECT-TYPE
	SYNTAX				Integer32 (0..10000)
	MAX-ACCESS			accessible-for-notify
	STATUS				current
	DESCRIPTION	        "The index of the auxiliary 2 sensor entry 1..96"
	::= { aux2SensorEntry 1 }

aux2SensorType		    OBJECT-TYPE
	SYNTAX				INTEGER { undefined(0), dcVoltage(38), dcCurrent(39), rmsVoltage(41), rmsCurrent(42), activePower(43), reactivePower(44) }
	MAX-ACCESS  		read-only
	STATUS				current
	DESCRIPTION	        "Auxiliary 2 Sensor Type"
	::= { aux2SensorEntry 2 }

aux2SensorDescription    OBJECT-TYPE
	SYNTAX				DisplayString
	MAX-ACCESS  		read-only
	STATUS				current
	DESCRIPTION	        "Auxiliary 2 Sensor Description"
	::= { aux2SensorEntry 3 }
    
aux2SensorConnector      OBJECT-TYPE
	SYNTAX				Integer32 (1..16)
	MAX-ACCESS  		read-only
	STATUS				current
	DESCRIPTION	        "Connector where the auxiliary 2 sensor is attached"
	::= { aux2SensorEntry 4 }
    
aux2SensorGroupNb        OBJECT-TYPE
	SYNTAX				Integer32 (1..8)
	MAX-ACCESS  		read-only
	STATUS				current
	DESCRIPTION	        "Auxiliary 2 Sensor's Group"
	::= { aux2SensorEntry 5 }
    
aux2SensorGroup          OBJECT-TYPE
	SYNTAX				DisplayString
	MAX-ACCESS  		read-only
	STATUS				current
	DESCRIPTION	        "Auxiliary 2 Sensor's Group Name"
	::= { aux2SensorEntry 6 }
    
aux2SensorValue			OBJECT-TYPE
	SYNTAX				INTEGER
	MAX-ACCESS			read-only
	STATUS				current
	DESCRIPTION	        "The value of the auxiliary 2 sensor reading. It is presented in tenths of degrees"
	::= { aux2SensorEntry 7 }
	
aux2SensorUnit			OBJECT-TYPE
	SYNTAX				Integer32 (0..1)
	MAX-ACCESS			read-only
	STATUS				current
	DESCRIPTION	        "The measuremnet unit for this sensor. Can be Celsius or Fahrenheit"
	::= { aux2SensorEntry 8 }
	
aux2SensorUnitName   	OBJECT-TYPE
	SYNTAX				DisplayString
	MAX-ACCESS			read-only
	STATUS				current
	DESCRIPTION	        "The measuremnet unit for this sensor in readable format"
	::= { aux2SensorEntry 9 }
	
aux2SensorStatus			OBJECT-TYPE
	SYNTAX				INTEGER {notconnected(0), normal(1), prealert(2), alert(3), acknowledged(4), dismissed(5), disconnected(6) }
	MAX-ACCESS			read-write
	STATUS				current
	DESCRIPTION	        "The status of the auxiliary 2 sensor"
	::= { aux2SensorEntry 10 }
	
aux2SensorMinThreshold	OBJECT-TYPE
	SYNTAX				Integer32 (0..1000)
	MAX-ACCESS			read-write
	STATUS				current
	DESCRIPTION	        "The value of the sensor lower threshold"
	::= { aux2SensorEntry 11 }
	
aux2SensorMaxThreshold	OBJECT-TYPE
	SYNTAX				Integer32 (0..1000)
	MAX-ACCESS			read-write
	STATUS				current
	DESCRIPTION	        "The value of the sensor upper threshold"
	::= { aux2SensorEntry 12 }
	
aux2SensorMinWarnThreshold	OBJECT-TYPE
	SYNTAX				Integer32 (0..1000)
	MAX-ACCESS			read-write
	STATUS				current
	DESCRIPTION	        "The value of the sensor lower warning threshold"
	::= { aux2SensorEntry 13 }
	
aux2SensorMaxWarnThreshold	OBJECT-TYPE
	SYNTAX				Integer32 (0..1000)
	MAX-ACCESS			read-write
	STATUS				current
	DESCRIPTION	        "The value of the sensor upper warning threshold"
	::= { aux2SensorEntry 14 }
	

-- external sensors description

extSensorTable			OBJECT-TYPE
	SYNTAX	            SEQUENCE OF	ExtSensorEntry
	MAX-ACCESS          not-accessible
	STATUS	            current
	DESCRIPTION         "Table of external Sensors entries"
	::= { extSensors 1 }

extSensorEntry     		OBJECT-TYPE
    SYNTAX              ExtSensorEntry
	MAX-ACCESS          not-accessible
	STATUS	            current
	DESCRIPTION         "An external sensor entry"
	INDEX               { extSensorIndex }
	::= { extSensorTable 1 }

ExtSensorEntry ::= 
	SEQUENCE {
		extSensorIndex
			Integer32,
		extSensorType
			INTEGER,
		extSensorDescription
			DisplayString,
		extSensorConnector
			Integer32,
		extSensorGroupNb
			Integer32,
		extSensorGroup
			DisplayString,
        extSensorValue
            INTEGER,
		extSensorUnit
			Integer32,
		extSensorUnitName
			DisplayString,
		extSensorStatus
			INTEGER,
		extSensorMinThreshold
			Integer32,
		extSensorMaxThreshold
			Integer32,
		extSensorMinWarnThreshold
			Integer32,
		extSensorMaxWarnThreshold
			Integer32
	}

extSensorIndex			OBJECT-TYPE
	SYNTAX				Integer32 (0..10000)
	MAX-ACCESS			accessible-for-notify
	STATUS				current
	DESCRIPTION	        "The index of the external sensor entry 1..4"
	::= { extSensorEntry 1 }

extSensorType		    OBJECT-TYPE
	SYNTAX				INTEGER {  undefined(0), temperature(1), humidity(2), power(3), lowVoltage(4), current(5), aclmvVoltage(6), aclmpVoltage(7), aclmpPower(8),water(9), smoke(10), vibration(11), motion(12), glass(13), door(14), keypad(15), panicButton(16), keyStation(17), digInput(18), light(22), tacDio(26), rmsVoltage(41), rmsCurrent(42), activePower(43), reactivePower(44), aldsLeakLocation(45), aldsContinuity(46), tempHum(513), custom(32767), temperatureCombo(32769), humidityCombo(32770)  }
	MAX-ACCESS  		read-only
	STATUS				current
	DESCRIPTION	        "Sensor Type"
	::= { extSensorEntry 2 }

extSensorDescription    OBJECT-TYPE
	SYNTAX				DisplayString
	MAX-ACCESS  		read-only
	STATUS				current
	DESCRIPTION	        "Sensor Description"
	::= { extSensorEntry 3 }
    
extSensorConnector      OBJECT-TYPE
	SYNTAX				Integer32 (1..16)
	MAX-ACCESS  		read-only
	STATUS				current
	DESCRIPTION	        "Connector where the sensor is attached"
	::= { extSensorEntry 4 }
    
extSensorGroupNb        OBJECT-TYPE
	SYNTAX				Integer32 (1..8)
	MAX-ACCESS  		read-only
	STATUS				current
	DESCRIPTION	        "Sensor's Group"
	::= { extSensorEntry 5 }
    
extSensorGroup          OBJECT-TYPE
	SYNTAX				DisplayString
	MAX-ACCESS  		read-only
	STATUS				current
	DESCRIPTION	        "Sensor's Group Name"
	::= { extSensorEntry 6 }
    
extSensorValue			OBJECT-TYPE
	SYNTAX				INTEGER { closed(0), open(1), normal(2), break(3) }
	MAX-ACCESS			read-only
	STATUS				current
	DESCRIPTION	        "The value of the external sensor reading. For temperature, voltage, current or low voltage,  it is presented in tenths of degrees/volts"
	::= { extSensorEntry 7 }
	
extSensorUnit			OBJECT-TYPE
	SYNTAX				Integer32 (0..1)
	MAX-ACCESS			read-only
	STATUS				current
	DESCRIPTION	        "The measuremnet unit for this sensor. It is important only for temperature"
	::= { extSensorEntry 8 }
	
extSensorUnitName   	OBJECT-TYPE
	SYNTAX				DisplayString
	MAX-ACCESS			read-only
	STATUS				current
	DESCRIPTION	        "The measuremnet unit for this sensor in readable format"
	::= { extSensorEntry 9 }
	
extSensorStatus			OBJECT-TYPE
	SYNTAX				INTEGER {notconnected(0), normal(1), prealert(2), alert(3), acknowledged(4), dismissed(5), disconnected(6) }
	MAX-ACCESS			read-write
	STATUS				current
	DESCRIPTION	        "The status of the sensor"
	::= { extSensorEntry 10 }
	
extSensorMinThreshold	OBJECT-TYPE
	SYNTAX				Integer32 (0..1000)
	MAX-ACCESS			read-write
	STATUS				current
	DESCRIPTION	        "The value of the sensor lower threshold"
	::= { extSensorEntry 11 }
	
extSensorMaxThreshold	OBJECT-TYPE
	SYNTAX				Integer32 (0..1000)
	MAX-ACCESS			read-write
	STATUS				current
	DESCRIPTION	        "The value of the sensor upper threshold"
	::= { extSensorEntry 12 }
	
extSensorMinWarnThreshold	OBJECT-TYPE
	SYNTAX				Integer32 (0..1000)
	MAX-ACCESS			read-write
	STATUS				current
	DESCRIPTION	        "The value of the sensor lower warning threshold"
	::= { extSensorEntry 13 }
	
extSensorMaxWarnThreshold	OBJECT-TYPE
	SYNTAX				Integer32 (0..1000)
	MAX-ACCESS			read-write
	STATUS				current
	DESCRIPTION	        "The value of the sensor upper warning threshold"
	::= { extSensorEntry 14 }
	
extSensorAclmTable		OBJECT-TYPE
	SYNTAX	            SEQUENCE OF	ExtSensorAclmValues
	MAX-ACCESS          not-accessible
	STATUS	            current
	DESCRIPTION         "Table of external Sensors entries"
	::= { extSensors 2 }

extSensorAclmValues		OBJECT-TYPE
    SYNTAX              ExtSensorAclmValues
	MAX-ACCESS          not-accessible
	STATUS	            current
	DESCRIPTION         "An external sensor entry"
	INDEX               { extSensorAclmIndex }
	::= { extSensorAclmTable 1 }

ExtSensorAclmValues ::=
        SEQUENCE {
                extSensorAclmIndex
                        Integer32,
                extSensorPeakValue
                        Integer32,
                extSensorFrequency
                        Integer32,
                extSensorCurrent
                        Integer32,
                extSensorSpikes
                        Integer32,
                extSensorSwells
                        Integer32,
                extSensorSags
                        Integer32,
                extSensorRelay
                        INTEGER,
                extSensorAclmMinThreshold
                        Integer32,
                extSensorAclmMaxThreshold
                        Integer32
        }

extSensorAclmIndex      OBJECT-TYPE
	SYNTAX				Integer32 (0..1000)
	MAX-ACCESS			read-only
	STATUS				current
	DESCRIPTION	        "Index of the sensor in the list"
	::= { extSensorAclmValues 1 }
        
extSensorPeakValue	    OBJECT-TYPE
	SYNTAX				Integer32 (0..1000)
	MAX-ACCESS			read-only
	STATUS				current
	DESCRIPTION	        "The peak value of the ACLM sensor presensted in tenths of volts/watts"
	::= { extSensorAclmValues 2 }
	
extSensorFrequency	    OBJECT-TYPE
	SYNTAX				Integer32 (0..1000)
	MAX-ACCESS			read-only
	STATUS				current
	DESCRIPTION	        "Frequency measured by the ACLM sensor presensted in tenths of Hz"
	::= { extSensorAclmValues 3 }
	
extSensorCurrent	    OBJECT-TYPE
	SYNTAX				Integer32 (0..1000)
	MAX-ACCESS			read-only
	STATUS				current
	DESCRIPTION	        "Current measured by the ACLM sensor presensted in tenths of A(mpers)"
	::= { extSensorAclmValues 4 }
	
extSensorSpikes	        OBJECT-TYPE
	SYNTAX				Integer32 (0..1000)
	MAX-ACCESS			read-only
	STATUS				current
	DESCRIPTION	        "Number of spikes read"
	::= { extSensorAclmValues 5 }
	
extSensorSwells	        OBJECT-TYPE
	SYNTAX				Integer32 (0..1000)
	MAX-ACCESS			read-only
	STATUS				current
	DESCRIPTION	        "Number of swells read"
	::= { extSensorAclmValues 6 }
	
extSensorSags	        OBJECT-TYPE
	SYNTAX				Integer32 (0..1000)
	MAX-ACCESS			read-only
	STATUS				current
	DESCRIPTION	        "Number of sags read"
	::= { extSensorAclmValues 7 }

extSensorRelay          OBJECT-TYPE
    SYNTAX              INTEGER { closed(0), open(1) }
	MAX-ACCESS			read-only
	STATUS				current
	DESCRIPTION	        "Relay status"
	::= { extSensorAclmValues 8 }

extSensorAclmMinThreshold	        OBJECT-TYPE
	SYNTAX				Integer32 (0..1000)
	MAX-ACCESS			read-only
	STATUS				current
	DESCRIPTION	        "Minimum Threshold"
	::= { extSensorAclmValues 9 }

extSensorAclmMaxThreshold	        OBJECT-TYPE
	SYNTAX				Integer32 (0..1000)
	MAX-ACCESS			read-only
	STATUS				current
	DESCRIPTION	        "Maximum Threshold"
	::= { extSensorAclmValues 10 }


-- database version 3 external sensors description

allExternalSensorTable   OBJECT-TYPE
  SYNTAX                SEQUENCE OF AllExternalSensorEntry  
  MAX-ACCESS            not-accessible
  STATUS                current
  DESCRIPTION           "Table of external Sensors entries"
  ::= { allExternalSensors 1 }

allExternalSensorEntry   OBJECT-TYPE
  SYNTAX                AllExternalSensorEntry
  MAX-ACCESS            not-accessible
  STATUS                current
  DESCRIPTION           "An external sensor entry"
  INDEX                 { allExternalSensorIndex }
  ::= { allExternalSensorTable 1 }

AllExternalSensorEntry ::=
  SEQUENCE {
    allExternalSensorIndex
      Integer32,
    allExternalSensorUID
      Integer32,
    allExternalSensorType
      INTEGER,
    allExternalSensorDescription
      DisplayString,
    allExternalSensorConnector
      DisplayString,
    allExternalSensorGroupNb
      Integer32,
    allExternalSensorGroup
      DisplayString,
    allExternalSensorValue
      DisplayString,
    allExternalSensorStatus
      INTEGER,
    allExternalSensorMinThreshold
      DisplayString,
    allExternalSensorMaxThreshold
      DisplayString,
    allExternalSensorMinWarnThreshold
      DisplayString,
    allExternalSensorMaxWarnThreshold
      DisplayString,
    allExternalSensorIntValue
      Integer32,
    allExternalSensorUnit
      DisplayString
  }

allExternalSensorIndex     OBJECT-TYPE
  SYNTAX            Integer32 (0..10000) 
  MAX-ACCESS        accessible-for-notify
  STATUS            current   
  DESCRIPTION       "The index of external Sensor entry 1..750"
  ::= { allExternalSensorEntry 1 }

allExternalSensorUID     OBJECT-TYPE
  SYNTAX           Integer32
  MAX-ACCESS       read-only
  STATUS           current
  DESCRIPTION      "Sensor UID"
  ::= { allExternalSensorEntry 2 }

allExternalSensorType      OBJECT-TYPE
  SYNTAX           INTEGER {undefined(0), temperature(1), humidity(2), power(3), lowVoltage(4), 
                            current(5), aclmvVoltage(6), aclmpVoltage(7), aclmpPower(8),water(9), 
                            smoke(10), vibration(11), motion(12), glass(13), door(14), keypad(15), 
                            panicButton(16), keyStation(17), digInput(18), light(22), tacDio(26), 
                            acVoltage(36), acCurrent(37), dcVoltage(38), dcCurrent(39), rmsVoltage(41),
                            rmsCurrent(42), activePower(43), reactivePower(44), aldsLeakLocation(45),
                            aldsContinuity(46), tempHum(513), custom(32767), temperatureCombo(32769), 
                            humidityCombo(32770)  }
  MAX-ACCESS       read-only
  STATUS           current
  DESCRIPTION      "Sensor Type"
  ::= { allExternalSensorEntry 3 }

allExternalSensorDescription     OBJECT-TYPE
  SYNTAX				DisplayString
	MAX-ACCESS    read-only
	STATUS				current
	DESCRIPTION	  "Sensor Description"
	::= { allExternalSensorEntry 4 }

allExternalSensorConnector     OBJECT-TYPE
  SYNTAX				DisplayString
	MAX-ACCESS    read-only
	STATUS				current
	DESCRIPTION	  "Connector where the sensor is attached"
	::= { allExternalSensorEntry 5 }

allExternalSensorGroupNb     OBJECT-TYPE
	SYNTAX				Integer32 (1..8)
	MAX-ACCESS  	read-only
	STATUS				current
	DESCRIPTION	  "Sensor's Group"
	::= { allExternalSensorEntry 6 }

allExternalSensorGroup     OBJECT-TYPE
	SYNTAX				DisplayString
	MAX-ACCESS  	read-only
	STATUS				current
	DESCRIPTION	  "Sensor's Group Name"
	::= { allExternalSensorEntry 7 }

allExternalSensorValue     OBJECT-TYPE
  SYNTAX        DisplayString
  MAX-ACCESS    read-write
  STATUS        current
  DESCRIPTION   "Value of external sensor with unit separated by space. Value is writable if sensor is Remote Output relay or Power Relay"
  ::= { allExternalSensorEntry 8 }

allExternalSensorStatus      OBJECT-TYPE
  SYNTAX        INTEGER { notconnected(0), normal(1), prealert(2), alert(3), acknowledged(4), 
                          dismissed(5), disconnected(6) }
  MAX-ACCESS    read-write
  STATUS        current
  DESCRIPTION   "The status of the sensor"
  ::= { allExternalSensorEntry 9 }

allExternalSensorMinThreshold	OBJECT-TYPE
	SYNTAX				DisplayString
	MAX-ACCESS		read-write
	STATUS				current
	DESCRIPTION	  "The value of the sensor lower threshold with unit"
	::= { allExternalSensorEntry 10 }
	
allExternalSensorMaxThreshold	OBJECT-TYPE
	SYNTAX				DisplayString
	MAX-ACCESS		read-write
	STATUS				current
	DESCRIPTION	  "The value of the sensor upper threshold with unit"
	::= { allExternalSensorEntry 11 }
	
allExternalSensorMinWarnThreshold	OBJECT-TYPE
	SYNTAX				DisplayString
	MAX-ACCESS		read-write
	STATUS				current
	DESCRIPTION	  "The value of the sensor lower warning threshold with unit"
	::= { allExternalSensorEntry 12 }
	
allExternalSensorMaxWarnThreshold	OBJECT-TYPE
	SYNTAX				DisplayString
	MAX-ACCESS		read-write
	STATUS				current
	DESCRIPTION	  "The value of the sensor upper warning threshold with unit"
	::= { allExternalSensorEntry 13 }
	
allExternalSensorIntValue	OBJECT-TYPE
	SYNTAX				Integer32
	MAX-ACCESS  	read-write
	STATUS				current
	DESCRIPTION	  "Sensors value in integer after multiplying by 1000. Divide by 1000.0 to get actual value. Value (multiplied by 1000) is writable if sensor is Remote Output relay or Power Relay"
	::= { allExternalSensorEntry 14 }
	
allExternalSensorUnit	OBJECT-TYPE
	SYNTAX				DisplayString
	MAX-ACCESS		read-only
	STATUS				current
	DESCRIPTION	  "The unit of the corresponding sensor in string (without any value prefix)"
	::= { allExternalSensorEntry 15 }
	
allExternalSensorAclmTable		OBJECT-TYPE
	SYNTAX	            SEQUENCE OF	AllExternalSensorAclmValues
	MAX-ACCESS          not-accessible
	STATUS	            current
	DESCRIPTION         "Table of external Sensors entries"
	::= { allExternalSensors 2 }
 
allExternalSensorAclmValues		OBJECT-TYPE
  SYNTAX              AllExternalSensorAclmValues
	MAX-ACCESS          not-accessible
	STATUS	            current
	DESCRIPTION         "An external sensor entry"
	INDEX               { allExternalSensorAclmIndex }
	::= { allExternalSensorAclmTable 1 }   


AllExternalSensorAclmValues ::=
  SEQUENCE {
    allExternalSensorAclmIndex
      Integer32,
    allExternalSensorPeakValue
      DisplayString,
    allExternalSensorFrequency
      DisplayString,
    allExternalSensorCurrent
      DisplayString,
    allExternalSensorSpikes
      Integer32,
    allExternalSensorSwells
      Integer32,
    allExternalSensorSags
      Integer32,
    allExternalSensorRelay
      INTEGER,
    allExternalSensorAclmMinThreshold
      DisplayString,
    allExternalSensorAclmMaxThreshold
      DisplayString
  }

allExternalSensorAclmIndex      OBJECT-TYPE
	SYNTAX				Integer32 (0..1000)
	MAX-ACCESS			read-only
	STATUS				current
	DESCRIPTION	  "Index of the sensor in the list"
	::= { allExternalSensorAclmValues 1 }

allExternalSensorPeakValue	    OBJECT-TYPE
	SYNTAX				DisplayString
	MAX-ACCESS		read-only
	STATUS				current
	DESCRIPTION	 "The peak value of the ACLM sensor and unit separated by space"
	::= { allExternalSensorAclmValues 2 }
	
allExternalSensorFrequency	    OBJECT-TYPE
	SYNTAX				DisplayString
	MAX-ACCESS	  read-only
	STATUS				current
	DESCRIPTION	  "Frequency measured by the ACLM sensor and unit separated by space"
	::= { allExternalSensorAclmValues 3 }
	
allExternalSensorCurrent	    OBJECT-TYPE
	SYNTAX				DisplayString
	MAX-ACCESS		read-only
	STATUS				current
	DESCRIPTION	  "Current measured by the ACLM sensor and unit separated by space"
	::= { allExternalSensorAclmValues 4 }
	
allExternalSensorSpikes	        OBJECT-TYPE
	SYNTAX				Integer32 (0..1000)
	MAX-ACCESS		read-only
	STATUS				current
	DESCRIPTION	  "Number of spikes read"
	::= { allExternalSensorAclmValues 5 }
	
allExternalSensorSwells	        OBJECT-TYPE
	SYNTAX				Integer32 (0..1000)
	MAX-ACCESS		read-only
	STATUS				current
	DESCRIPTION	  "Number of swells read"
	::= { allExternalSensorAclmValues 6 }
	
allExternalSensorSags	        OBJECT-TYPE
	SYNTAX				Integer32 (0..1000)
	MAX-ACCESS		read-only
	STATUS				current
	DESCRIPTION	  "Number of sags read"
	::= { allExternalSensorAclmValues 7 }

allExternalSensorRelay          OBJECT-TYPE
  SYNTAX        INTEGER { closed(0), open(1) }
	MAX-ACCESS		read-only
	STATUS				current
	DESCRIPTION	  "Relay status"
	::= { allExternalSensorAclmValues 8 }

allExternalSensorAclmMinThreshold	    OBJECT-TYPE
	SYNTAX				DisplayString
	MAX-ACCESS	  read-only
	STATUS				current
	DESCRIPTION	  "Minimum Threshold"
	::= { allExternalSensorAclmValues 9 }

allExternalSensorAclmMaxThreshold	    OBJECT-TYPE
	SYNTAX				DisplayString
	MAX-ACCESS	  read-only
	STATUS				current
	DESCRIPTION	  "Maximum Threshold"
	::= { allExternalSensorAclmValues 10 }

-- external Tac sensors description

tacSensorTable		OBJECT-TYPE
	SYNTAX	            SEQUENCE OF	TacSensorEntry
	MAX-ACCESS          not-accessible
	STATUS	            current
	DESCRIPTION         "Table of Tac sensors entries"
	::= { tacSensors 1 }

tacSensorEntry		OBJECT-TYPE
    SYNTAX              TacSensorEntry
	MAX-ACCESS          not-accessible
	STATUS	            current
	DESCRIPTION         "A tac sensor entry"
	INDEX               { tacSensorIndex }
	::= { tacSensorTable 1 }

TacSensorEntry ::= 
	SEQUENCE {
		tacSensorIndex
			Integer32,
		tacSensorType
			INTEGER,
		tacSensorDescription
			DisplayString,
        tacSensorConnector
            Integer32,
		tacSensorGroupNb
			Integer32,
		tacSensorGroup
			DisplayString,
        tacSensorValue
            Integer32,
		tacSensorUnit
			Integer32,
		tacSensorUnitName
			DisplayString,
		tacSensorStatus
			INTEGER,
		tacSensorMinThreshold
			Integer32,
		tacSensorMaxThreshold
			Integer32,
		tacSensorMinWarnThreshold
			Integer32,
		tacSensorMaxWarnThreshold
			Integer32
	}

tacSensorIndex			OBJECT-TYPE
	SYNTAX				Integer32 (0..10000)
	MAX-ACCESS			accessible-for-notify
	STATUS				current
	DESCRIPTION	        "The index of the Tac sensor entry 1..4"
	::= { tacSensorEntry 1 }

tacSensorType		    OBJECT-TYPE
	SYNTAX				INTEGER {  undefined(0), tac(29) }
	MAX-ACCESS  		read-only
	STATUS				current
	DESCRIPTION	        "Tac Sensor Type"
	::= { tacSensorEntry 2 }

tacSensorDescription    OBJECT-TYPE
	SYNTAX				DisplayString
	MAX-ACCESS  		read-only
	STATUS				current
	DESCRIPTION	        "Tac Sensor Description"
	::= { tacSensorEntry 3 }
    
tacSensorConnector      OBJECT-TYPE
	SYNTAX		        Integer32 (1..16)
	MAX-ACCESS  		read-only
	STATUS			current
	DESCRIPTION	        "Connector where the Tac sensor is attached"
	::= { tacSensorEntry 4 }
    
tacSensorGroupNb        OBJECT-TYPE
	SYNTAX				Integer32 (1..8)
	MAX-ACCESS  		read-only
	STATUS				current
	DESCRIPTION	        "Tac Sensor's Group"
	::= { tacSensorEntry 5 }
    
tacSensorGroup          OBJECT-TYPE
	SYNTAX				DisplayString
	MAX-ACCESS  		read-only
	STATUS				current
	DESCRIPTION	        "Tac Sensor's Group Name"
	::= { tacSensorEntry 6 }
    
tacSensorValue			OBJECT-TYPE
	SYNTAX				Integer32
	MAX-ACCESS			read-only
	STATUS				current
	DESCRIPTION	        "The value of the Tac sensor reading."
	::= { tacSensorEntry 7 }
	
tacSensorUnit			OBJECT-TYPE
	SYNTAX				Integer32 (0..1)
	MAX-ACCESS			read-only
	STATUS				current
	DESCRIPTION	        "The measuremnet unit for this sensor. Can be Celsius or Fahrenheit"
	::= { tacSensorEntry 8 }
	
tacSensorUnitName   	OBJECT-TYPE
	SYNTAX				DisplayString
	MAX-ACCESS			read-only
	STATUS				current
	DESCRIPTION	        "The measuremnet unit for this sensor in readable format"
	::= { tacSensorEntry 9 }
	
tacSensorStatus			OBJECT-TYPE
	SYNTAX				INTEGER {notconnected(0), normal(1), prealert(2), alert(3), acknowledged(4), dismissed(5), disconnected(6) }
	MAX-ACCESS			read-write
	STATUS				current
	DESCRIPTION	        "The status of the Tac sensor"
	::= { tacSensorEntry 10 }
	
tacSensorMinThreshold	OBJECT-TYPE
	SYNTAX				Integer32 (0..1000)
	MAX-ACCESS			read-write
	STATUS				current
	DESCRIPTION	        "The value of the sensor lower threshold"
	::= { tacSensorEntry 11 }
	
tacSensorMaxThreshold	OBJECT-TYPE
	SYNTAX				Integer32 (0..1000)
	MAX-ACCESS			read-write
	STATUS				current
	DESCRIPTION	        "The value of the sensor upper threshold"
	::= { tacSensorEntry 12 }
	
tacSensorMinWarnThreshold	OBJECT-TYPE
	SYNTAX				Integer32 (0..1000)
	MAX-ACCESS			read-write
	STATUS				current
	DESCRIPTION	        "The value of the sensor lower warning threshold"
	::= { tacSensorEntry 13 }
	
tacSensorMaxWarnThreshold	OBJECT-TYPE
	SYNTAX				Integer32 (0..1000)
	MAX-ACCESS			read-write
	STATUS				current
	DESCRIPTION	        "The value of the sensor upper warning threshold"
	::= { tacSensorEntry 14 }
	

	
-- dry contacts description

digInputTable	   	OBJECT-TYPE
	SYNTAX	            SEQUENCE OF	DryContactEntry
	MAX-ACCESS          not-accessible
	STATUS	            current
	DESCRIPTION         "Table of external Sensors entries"
	::= { digInputs 1 }

digInputEntry   		OBJECT-TYPE
    SYNTAX              DryContactEntry
	MAX-ACCESS          not-accessible
	STATUS	            current
	DESCRIPTION         "A dry contact entry"
	INDEX               { digInputIndex }
	::= { digInputTable 1 }

DryContactEntry ::= 
	SEQUENCE {
		digInputIndex
			Integer32,
		digInputType
			INTEGER,
		digInputDescription
			DisplayString,
		digInputConnector
			Integer32,
		digInputGroupNb
			Integer32,
		digInputGroup
			DisplayString,
        digInputValue
            INTEGER,
		digInputStatus
			INTEGER,
		digInputNormalValue
			INTEGER
	}

digInputIndex		OBJECT-TYPE
	SYNTAX				Integer32 (0..10000)
	MAX-ACCESS			accessible-for-notify
	STATUS				current
	DESCRIPTION	        "The index of the external sensor entry 1..4"
	::= { digInputEntry 1 }

digInputType		    OBJECT-TYPE
	SYNTAX				INTEGER { digInput(18) }
	MAX-ACCESS  		read-only
	STATUS				current
	DESCRIPTION	        "Sensor Type. Only dry contact type will be used"
	::= { digInputEntry 2 }

digInputDescription  OBJECT-TYPE
	SYNTAX				DisplayString
	MAX-ACCESS  		read-only
	STATUS				current
	DESCRIPTION	        "Sensor Description"
	::= { digInputEntry 3 }
    
digInputConnector    OBJECT-TYPE
	SYNTAX				Integer32 (1..8)
	MAX-ACCESS  		read-only
	STATUS				current
	DESCRIPTION	        "Connector where the sensor is attached"
	::= { digInputEntry 4 }
    
digInputGroupNb      OBJECT-TYPE
	SYNTAX				Integer32 (1..8)
	MAX-ACCESS  		read-only
	STATUS				current
	DESCRIPTION	        "Sensor's Group"
	::= { digInputEntry 5 }
    
digInputGroup        OBJECT-TYPE
	SYNTAX				DisplayString
	MAX-ACCESS  		read-only
	STATUS				current
	DESCRIPTION	        "Sensor's Group Name"
	::= { digInputEntry 6 }
    
digInputValue		OBJECT-TYPE
	SYNTAX				INTEGER { closed(0), open(1) }
	MAX-ACCESS			read-only
	STATUS				current
	DESCRIPTION	        "The value of the dry contact reading."
	::= { digInputEntry 7 }
	
digInputStatus		OBJECT-TYPE
	SYNTAX				INTEGER {notconnected(0), normal(1), prealert(2), alert(3), acknowledged(4), dismissed(5), disconnected(6), reserved(10) }
	MAX-ACCESS			read-write
	STATUS				current
	DESCRIPTION	        "The status of the sensor"
	::= { digInputEntry 8 }
	
digInputNormalValue  OBJECT-TYPE
	SYNTAX				INTEGER { closed(0), open(1) }
	MAX-ACCESS			read-write
	STATUS				current
	DESCRIPTION	        "The normal value of the dry contact reading"
	::= { digInputEntry 9 }
	
	
-- remote inputs description

remoteInputTable	   	OBJECT-TYPE
	SYNTAX	            SEQUENCE OF	RemoteInputEntry
	MAX-ACCESS          not-accessible
	STATUS	            current
	DESCRIPTION         "Table of Remote Inputs entries"
	::= { remoteInputs 1 }

remoteInputEntry   		OBJECT-TYPE
    SYNTAX              RemoteInputEntry
	MAX-ACCESS          not-accessible
	STATUS	            current
	DESCRIPTION         "A remote input entry"
	INDEX               { remoteInputIndex }
	::= { remoteInputTable 1 }

RemoteInputEntry ::= 
	SEQUENCE {
		remoteInputIndex
			Integer32,
		remoteInputType
			INTEGER,
		remoteInputDescription
			DisplayString,
		remoteInputConnector
			Integer32,
		remoteInputGroupNb
			Integer32,
		remoteInputGroup
			DisplayString,
        remoteInputValue
            INTEGER,
		remoteInputStatus
			INTEGER,
		remoteInputNormalValue
			INTEGER
	}

remoteInputIndex		OBJECT-TYPE
	SYNTAX				Integer32 (0..10000)
	MAX-ACCESS			accessible-for-notify
	STATUS				current
	DESCRIPTION	        "The index of the remote input entry 1..4"
	::= { remoteInputEntry 1 }

remoteInputType		    OBJECT-TYPE
	SYNTAX				INTEGER { remoteInput(18) }
	MAX-ACCESS  		read-only
	STATUS				current
	DESCRIPTION	        "Sensor Type. Remote input contact type will be used"
	::= { remoteInputEntry 2 }

remoteInputDescription  OBJECT-TYPE
	SYNTAX				DisplayString
	MAX-ACCESS  		read-only
	STATUS				current
	DESCRIPTION	        "Sensor Description"
	::= { remoteInputEntry 3 }
    
remoteInputConnector    OBJECT-TYPE
	SYNTAX				Integer32 (1..256)
	MAX-ACCESS  		read-only
	STATUS				current
	DESCRIPTION	        "Connector where the sensor is attached"
	::= { remoteInputEntry 4 }
    
remoteInputGroupNb      OBJECT-TYPE
	SYNTAX				Integer32 (1..8)
	MAX-ACCESS  		read-only
	STATUS				current
	DESCRIPTION	        "Sensor's Group"
	::= { remoteInputEntry 5 }
    
remoteInputGroup        OBJECT-TYPE
	SYNTAX				DisplayString
	MAX-ACCESS  		read-only
	STATUS				current
	DESCRIPTION	        "Sensor's Group Name"
	::= { remoteInputEntry 6 }
    
remoteInputValue		OBJECT-TYPE
	SYNTAX				INTEGER { closed(0), open(1) }
	MAX-ACCESS			read-only
	STATUS				current
	DESCRIPTION	        "The value of the remote input reading."
	::= { remoteInputEntry 7 }
	
remoteInputStatus		OBJECT-TYPE
	SYNTAX				INTEGER {notconnected(0), normal(1), prealert(2), alert(3), acknowledged(4), dismissed(5), disconnected(6) }
	MAX-ACCESS			read-write
	STATUS				current
	DESCRIPTION	        "The status of the sensor"
	::= { remoteInputEntry 8 }
	
remoteInputNormalValue  OBJECT-TYPE
	SYNTAX				INTEGER { closed(0), open(1) }
	MAX-ACCESS			read-only
	STATUS				current
	DESCRIPTION	        "The normal value of the remote input reading"
	::= { remoteInputEntry 9 }
	
	
-- IP Devices description

ipDeviceTable           OBJECT-TYPE
    SYNTAX              SEQUENCE OF IpDeviceEntry
	MAX-ACCESS          not-accessible
	STATUS	            current
	DESCRIPTION         "Table of IP Devices entries"
	::= { ipDevices 1 }

ipDeviceEntry    		OBJECT-TYPE
    SYNTAX              IpDeviceEntry
	MAX-ACCESS          not-accessible
	STATUS	            current
	DESCRIPTION         "An IP Device entry"
	INDEX               { ipDeviceIndex }
	::= { ipDeviceTable 1 }

IpDeviceEntry ::= 
	SEQUENCE {
		ipDeviceIndex
			Integer32,
		ipDeviceAddress
			DisplayString,
		ipDeviceDescription
			DisplayString,
		ipDeviceGroupNb
			Integer32,
		ipDeviceGroup
			DisplayString,
		ipDeviceTimeout
			Integer32,
		ipDeviceRetries
			Integer32,
		ipDeviceValue
			INTEGER,
		ipDeviceStatus
			INTEGER
	}

ipDeviceIndex			OBJECT-TYPE
	SYNTAX				Integer32 (0..10000)
	MAX-ACCESS			accessible-for-notify
	STATUS				current
	DESCRIPTION	        "The index of the IP Device entry 1..8"
	::= { ipDeviceEntry 1 }

ipDeviceAddress   OBJECT-TYPE
	SYNTAX				DisplayString
	MAX-ACCESS  		read-only
	STATUS				current
	DESCRIPTION	        "IP Device URL"
	::= { ipDeviceEntry 2 }
    
ipDeviceDescription     OBJECT-TYPE
	SYNTAX				DisplayString
	MAX-ACCESS  		read-only
	STATUS				current
	DESCRIPTION	        "IP Device Description"
	::= { ipDeviceEntry 3 }
    
ipDeviceGroupNb         OBJECT-TYPE
	SYNTAX				Integer32 (1..8)
	MAX-ACCESS  		read-only
	STATUS				current
	DESCRIPTION	        "Index of the group the IP Device belongs to"
	::= { ipDeviceEntry 4 }
    
ipDeviceGroup           OBJECT-TYPE
	SYNTAX				DisplayString
	MAX-ACCESS  		read-only
	STATUS				current
	DESCRIPTION	        "Name of the group the IP Device belongs to"
	::= { ipDeviceEntry 5 }
    
ipDeviceTimeout         OBJECT-TYPE
	SYNTAX				Integer32 
	MAX-ACCESS  		read-only
	STATUS				current
	DESCRIPTION	        "IP Device ping timeout (in seconds)"
	::= { ipDeviceEntry 6 }
    
ipDeviceRetries         OBJECT-TYPE
	SYNTAX				Integer32 
	MAX-ACCESS  		read-only
	STATUS				current
	DESCRIPTION	        "Number of ping retries to the IP device, until responding"
	::= { ipDeviceEntry 7 }
    
ipDeviceValue           OBJECT-TYPE
	SYNTAX				INTEGER { notResponding(0), responding(1) }
	MAX-ACCESS  		read-only
	STATUS				current
	DESCRIPTION	        "Responding status"
	::= { ipDeviceEntry 8 }
    
ipDeviceStatus          OBJECT-TYPE
	SYNTAX				INTEGER {notconnected(0), normal(1), prealert(2), alert(3), acknowledged(4), dismissed(5), disconnected(6) }
	MAX-ACCESS  		read-write
	STATUS				current
	DESCRIPTION	        "Alarm status of the IP Device"
	::= { ipDeviceEntry 9 }

-- outRelays description

outRelayTable           OBJECT-TYPE
    SYNTAX              SEQUENCE OF OutRelayEntry
    MAX-ACCESS          not-accessible
    STATUS              current
    DESCRIPTION         "Table of output relays"
    ::= { outRelays 1 }

outRelayEntry           OBJECT-TYPE
    SYNTAX              OutRelayEntry
    MAX-ACCESS          not-accessible
    STATUS              current
    DESCRIPTION         "An output relay entry"
    INDEX               { outRelayIndex }
    ::= { outRelayTable 1 }

OutRelayEntry ::=
    SEQUENCE {
        outRelayIndex
            Integer32,
        outRelayDescription
            DisplayString,            
        outRelayStatus
            INTEGER
    }

outRelayIndex           OBJECT-TYPE
    SYNTAX              Integer32 (0..10000)
    MAX-ACCESS          accessible-for-notify
    STATUS              current
    DESCRIPTION         "The index of relay"
    ::= { outRelayEntry 1 }

outRelayDescription     OBJECT-TYPE
    SYNTAX              DisplayString
    MAX-ACCESS          read-only
    STATUS              current
    DESCRIPTION         "Desciption/name associated with the output relay"
    ::= { outRelayEntry 2 }

outRelayStatus          OBJECT-TYPE
    SYNTAX              INTEGER { active(0), inactive(1) }
    MAX-ACCESS          read-write
    STATUS              current
    DESCRIPTION         "The status of the output relay"
    ::= { outRelayEntry 3 }    
    


-- remoteRelays description

remoteRelayTable           OBJECT-TYPE
    SYNTAX              SEQUENCE OF RemoteRelayEntry
    MAX-ACCESS          not-accessible
    STATUS              current
    DESCRIPTION         "Table of remote relays"
    ::= { remoteRelays 1 }

remoteRelayEntry           OBJECT-TYPE
    SYNTAX              RemoteRelayEntry
    MAX-ACCESS          not-accessible
    STATUS              current
    DESCRIPTION         "An output relay entry"
    INDEX               { remoteRelayIndex }
    ::= { remoteRelayTable 1 }

RemoteRelayEntry ::=
    SEQUENCE {
        remoteRelayIndex
            Integer32,
        remoteRelayDescription
            DisplayString,            
        remoteRelayStatus
            INTEGER
    }

remoteRelayIndex           OBJECT-TYPE
    SYNTAX              Integer32 (0..10000)
    MAX-ACCESS          accessible-for-notify
    STATUS              current
    DESCRIPTION         "The index of relay"
    ::= { remoteRelayEntry 1 }

remoteRelayDescription     OBJECT-TYPE
    SYNTAX              DisplayString
    MAX-ACCESS          read-only
    STATUS              current
    DESCRIPTION         "Desciption/name associated with the remote relay"
    ::= { remoteRelayEntry 2 }

remoteRelayStatus          OBJECT-TYPE
    SYNTAX              INTEGER { active(0), inactive(1) }
    MAX-ACCESS          read-write
    STATUS              current
    DESCRIPTION         "The status of the remote relay"
    ::= { remoteRelayEntry 3 }    
   
-- powerSupply description

pwrSupplyTable          OBJECT-TYPE
    SYNTAX              SEQUENCE OF PwrSupplyEntry
    MAX-ACCESS          not-accessible
    STATUS              current
    DESCRIPTION         "Table of power supplies"
    ::= { pwrSupplies 1 }

pwrSupplyEntry          OBJECT-TYPE
    SYNTAX              PwrSupplyEntry
    MAX-ACCESS          not-accessible
    STATUS              current
    DESCRIPTION         "An output relay entry"
    INDEX               { pwrSupplyIndex }
    ::= { pwrSupplyTable 1 }

PwrSupplyEntry ::=
    SEQUENCE {
        pwrSupplyIndex
            Integer32,
        pwrSupplyStatus
            INTEGER
    }

pwrSupplyIndex          OBJECT-TYPE
    SYNTAX              Integer32 (0..10000)
    MAX-ACCESS          accessible-for-notify
    STATUS              current
    DESCRIPTION         "The index of power supply"
    ::= { pwrSupplyEntry 1 }

pwrSupplyStatus          OBJECT-TYPE
    SYNTAX              INTEGER { failed(0), ok(1), na(2) }
    MAX-ACCESS          read-write
    STATUS              current
    DESCRIPTION         "The status of the output relay"
    ::= { pwrSupplyEntry 2 }    

-- events description

eventTable              OBJECT-TYPE
    SYNTAX              SEQUENCE OF EventEntry
    MAX-ACCESS          not-accessible
    STATUS              current
    DESCRIPTION         "Table of events"
    ::= { events 1 }

eventEntry              OBJECT-TYPE
    SYNTAX              EventEntry
    MAX-ACCESS          not-accessible
    STATUS              current
    DESCRIPTION         "An event entry"
    INDEX               { eventIndex }
    ::= { eventTable 1 }

EventEntry ::=
    SEQUENCE {
        eventIndex
            Integer32,
        eventDescription
            DisplayString,
        eventStatus
            INTEGER,
        eventValue
            Integer32
}

eventIndex              OBJECT-TYPE
    SYNTAX              Integer32 (0..10000)
    MAX-ACCESS          accessible-for-notify
    STATUS              current
    DESCRIPTION         "The index of the event"
    ::= { eventEntry 1 }

eventDescription        OBJECT-TYPE
    SYNTAX              DisplayString
    MAX-ACCESS          read-only
    STATUS              current
    DESCRIPTION         "Desciption/name associated with the event"
    ::= { eventEntry 2 }

eventStatus             OBJECT-TYPE
    SYNTAX              INTEGER { normal(1), alert(3), acknowledged(4), dismissed(5) }
    MAX-ACCESS          read-write
    STATUS              current
    DESCRIPTION         "The status of the event"
    ::= { eventEntry 3 }    

eventValue			OBJECT-TYPE
	SYNTAX				Integer32 (0..10000)
	MAX-ACCESS			read-only
	STATUS				current
	DESCRIPTION	        "The value of the sensor event reading. For temperature, voltage, current or low voltage,  it is presented in tenths of degrees/volts"
	::= { eventEntry 4 }
	

-- smartAlerts description

smartAlertTable         OBJECT-TYPE
    SYNTAX              SEQUENCE OF SmartAlertEntry
    MAX-ACCESS          not-accessible
    STATUS              current
    DESCRIPTION         "Table of smartAlerts"
    ::= { smartAlerts 1 }

smartAlertEntry         OBJECT-TYPE
    SYNTAX              SmartAlertEntry
    MAX-ACCESS          not-accessible
    STATUS              current
    DESCRIPTION         "A smartAlert entry"
    INDEX               { smartAlertIndex }
    ::= { smartAlertTable 1 }

SmartAlertEntry ::=
    SEQUENCE {
        smartAlertIndex
            Integer32,
        smartAlertDescription
            DisplayString,
        smartAlertStatus
            INTEGER
    }

smartAlertIndex         OBJECT-TYPE
    SYNTAX              Integer32 (0..10000)
    MAX-ACCESS          accessible-for-notify
    STATUS              current
    DESCRIPTION         "The index of the smartAlert"
    ::= { smartAlertEntry 1 }

smartAlertDescription   OBJECT-TYPE
    SYNTAX              DisplayString
    MAX-ACCESS          read-only
    STATUS              current
    DESCRIPTION         "Desciption/name associated with the smartAlert"
    ::= { smartAlertEntry 2 }

smartAlertStatus        OBJECT-TYPE
    SYNTAX              INTEGER { normal(1), alert(3), acknowledged(4), dismissed(5) }
    MAX-ACCESS          read-write
    STATUS              current
    DESCRIPTION         "The status of the smartAlert"
    ::= { smartAlertEntry 3 }    

-- smoke detectors description

smokeDetectorTable   	OBJECT-TYPE
	SYNTAX	            SEQUENCE OF	SmokeDetectorEntry
	MAX-ACCESS          not-accessible
	STATUS	            current
	DESCRIPTION         "Table of Smoke Detectors entries"
	::= { smokeDetectors 1 }

smokeDetectorEntry 		OBJECT-TYPE
    SYNTAX              SmokeDetectorEntry
	MAX-ACCESS          not-accessible
	STATUS	            current
	DESCRIPTION         "A smoke detector entry"
	INDEX               { smokeDetectorIndex }
	::= { smokeDetectorTable 1 }

SmokeDetectorEntry ::=
    SEQUENCE {
        smokeDetectorIndex
            Integer32,
        smokeDetectorDescription
            DisplayString,
		smokeDetectorGroupNb
			Integer32,
        smokeDetectorValue
            INTEGER,
		smokeDetectorStatus
			INTEGER
    }

smokeDetectorIndex		OBJECT-TYPE
	SYNTAX				Integer32 (0..10000)
	MAX-ACCESS			accessible-for-notify
	STATUS				current
	DESCRIPTION	        "The index of the smoke detector entry 1..8"
	::= { smokeDetectorEntry 1 }

smokeDetectorDescription    OBJECT-TYPE
	SYNTAX				DisplayString
	MAX-ACCESS  		read-only
	STATUS				current
	DESCRIPTION	        "Smoke Detector Description"
	::= { smokeDetectorEntry 2 }

smokeDetectorGroupNb    OBJECT-TYPE
	SYNTAX				Integer32 (1..8)
	MAX-ACCESS  		read-only
	STATUS				current
	DESCRIPTION	        "Sensor's Group"
	::= { smokeDetectorEntry 3 }
    
smokeDetectorValue   	OBJECT-TYPE
	SYNTAX				INTEGER { firePreAlert(0), preAlert(1), fire(2), ok(3), firePreAlertFault(4), preAlertFault(5), fireFault(6), fault(7) }
	MAX-ACCESS			read-only
	STATUS				current
	DESCRIPTION	        "The value of the smoke detector reading."
	::= { smokeDetectorEntry 4 }
	
smokeDetectorStatus		OBJECT-TYPE
	SYNTAX				INTEGER {notconnected(0), normal(1), prealert(2), alert(3), acknowledged(4), dismissed(5), disconnected(6) }
	MAX-ACCESS			read-write
	STATUS				current
	DESCRIPTION	        "The status of the smoke detector"
	::= { smokeDetectorEntry 5 }
	
-- IP Sensors    

ipSensorTable           OBJECT-TYPE
    SYNTAX              SEQUENCE OF IpSensorEntry
    MAX-ACCESS          not-accessible
    STATUS              current
    DESCRIPTION         "Table of IP Sensors entries"
    ::= { ipSensors 1 }

ipSensorEntry           OBJECT-TYPE
    SYNTAX              IpSensorEntry
    MAX-ACCESS          not-accessible
    STATUS              current
    DESCRIPTION         "An IP sensor entry"
    INDEX               { ipSensorIndex }
    ::= { ipSensorTable 1 }

IpSensorEntry ::=
    SEQUENCE {
		ipSensorIndex
			Integer32,
		ipSensorMicroUnit
			Integer32,
		ipSensorType
			INTEGER,
		ipSensorDescription
			DisplayString,
		ipSensorConnector
			Integer32,
		ipSensorGroupNb
			Integer32,
		ipSensorGroup
			DisplayString,
        ipSensorValue
            INTEGER,
		ipSensorUnit
			Integer32,
		ipSensorUnitName
			DisplayString,
		ipSensorStatus
			INTEGER,
		ipSensorMinThreshold
			Integer32,
		ipSensorMaxThreshold
			Integer32
    }

ipSensorIndex			OBJECT-TYPE
	SYNTAX				Integer32 (0..10000)
	MAX-ACCESS			accessible-for-notify
	STATUS				current
	DESCRIPTION	        "The index of the external sensor entry 1..88"
	::= { ipSensorEntry 1 }

ipSensorMicroUnit	    OBJECT-TYPE
	SYNTAX				Integer32 
	MAX-ACCESS			accessible-for-notify
	STATUS				current
	DESCRIPTION	        "The index of the Enviromux units the sensor belongs to Micro (1..8), E-1W (9..12) and Rebooter (13..14)"
	::= { ipSensorEntry 2 }

ipSensorType		    OBJECT-TYPE
	SYNTAX				INTEGER {  undefined(0), temperature(1), humidity(2), power(3), lowVoltage(4), current(5), aclmvVoltage(6), aclmpVoltage(7), aclmpPower(8),water(9), smoke(10), vibration(11), motion(12), glass(13), door(14), keypad(15), panicButton(16), keyStation(17), digInput(18), ipDevice(20), light(22), tacDio(26), outRelay(57), tempHum(513), custom(32767), temperatureCombo(32769), humidityCombo(32770)  }
	MAX-ACCESS  		read-only
	STATUS				current
	DESCRIPTION	        "Sensor Type"
	::= { ipSensorEntry 3 }

ipSensorDescription    OBJECT-TYPE
	SYNTAX				DisplayString
	MAX-ACCESS  		read-only
	STATUS				current
	DESCRIPTION	        "Sensor Description"
	::= { ipSensorEntry 4 }
    
ipSensorConnector      OBJECT-TYPE
	SYNTAX				Integer32 (1..16)
	MAX-ACCESS  		read-only
	STATUS				current
	DESCRIPTION	        "Connector where the sensor is attached on the Enviromux-Micro unit, -1 if internal"
	::= { ipSensorEntry 5 }
    
ipSensorGroupNb        OBJECT-TYPE
	SYNTAX				Integer32 (1..8)
	MAX-ACCESS  		read-only
	STATUS				current
	DESCRIPTION	        "Sensor's Group"
	::= { ipSensorEntry 6 }
    
ipSensorGroup          OBJECT-TYPE
	SYNTAX				DisplayString
	MAX-ACCESS  		read-only
	STATUS				current
	DESCRIPTION	        "Sensor's Group Name"
	::= { ipSensorEntry 7 }
    
ipSensorValue			OBJECT-TYPE
	SYNTAX				INTEGER
	MAX-ACCESS			read-write
	STATUS				current
	DESCRIPTION	        "The value of the external sensor reading. For temperature, voltage, current or low voltage, it is presented in tenths of degrees/volts. For Digital Inputs/Outputs and IP Devices, value is presented as 1 or 0. Value is writable if sensor is Output relay"
	::= { ipSensorEntry 8 }
	
ipSensorUnit			OBJECT-TYPE
	SYNTAX				Integer32 (0..1)
	MAX-ACCESS			read-only
	STATUS				current
	DESCRIPTION	        "The measuremnet unit for this sensor. It is important only for temperature"
	::= { ipSensorEntry 9 }
	
ipSensorUnitName   	OBJECT-TYPE
	SYNTAX				DisplayString
	MAX-ACCESS			read-only
	STATUS				current
	DESCRIPTION	        "The measuremnet unit for this sensor in readable format"
	::= { ipSensorEntry 10 }
	
ipSensorStatus			OBJECT-TYPE
	SYNTAX				INTEGER {notconnected(0), normal(1), prealert(2), alert(3), acknowledged(4), dismissed(5), disconnected(6) }
	MAX-ACCESS			read-write
	STATUS				current
	DESCRIPTION	        "The status of the sensor"
	::= { ipSensorEntry 11 }
	
ipSensorMinThreshold	OBJECT-TYPE
	SYNTAX				Integer32 (0..1000)
	MAX-ACCESS			read-only
	STATUS				current
	DESCRIPTION	        "The value of the sensor lower threshold"
	::= { ipSensorEntry 12 }
	
ipSensorMaxThreshold	OBJECT-TYPE
	SYNTAX				Integer32 (0..1000)
	MAX-ACCESS			read-only
	STATUS				current
	DESCRIPTION	        "The value of the sensor upper threshold"
	::= { ipSensorEntry 13 }

-- Message Registers description

msgRegistersTable       OBJECT-TYPE
    SYNTAX              SEQUENCE OF MsgRegistersEntry
    MAX-ACCESS          not-accessible
    STATUS              current
    DESCRIPTION         "Table of message registers"
    ::= { msgRegisters 1 }

msgRegistersEntry       OBJECT-TYPE
    SYNTAX              MsgRegistersEntry
    MAX-ACCESS          not-accessible
    STATUS              current
    DESCRIPTION         "An input message entry"
    INDEX               { msgRegistersIndex }
    ::= { msgRegistersTable 1 }

MsgRegistersEntry ::=
    SEQUENCE {
        msgRegistersIndex
            Integer32,
		msgRegistersDescription
			DisplayString,
        msgRegistersStatus
            INTEGER
    }

msgRegistersIndex        OBJECT-TYPE
    SYNTAX              Integer32 (1..1)
    MAX-ACCESS          read-only
    STATUS              current
    DESCRIPTION         "The index of message register"
    ::= { msgRegistersEntry 1 }

msgRegistersDescription OBJECT-TYPE
    SYNTAX              DisplayString
    MAX-ACCESS          read-write
    STATUS              current
    DESCRIPTION         "The content of the message"
    ::= { msgRegistersEntry 2 }

msgRegistersStatus      OBJECT-TYPE
    SYNTAX              INTEGER { free(0), busy(1)}
	MAX-ACCESS          read-only
    STATUS              current
    DESCRIPTION         "The status of the message register"
    ::= { msgRegistersEntry 3 }    

--Network Configure

netConfIPv4Mode  	OBJECT-TYPE
	SYNTAX				INTEGER {dhcp(0), static(1)}
	MAX-ACCESS  		read-write
	STATUS				current
	DESCRIPTION		    "Method of acquiring IP settings"
	::= { netConfRegisters 1 }

netConfIPv4Addr  	OBJECT-TYPE
	SYNTAX				DisplayString
	MAX-ACCESS  		read-write
	STATUS				current
	DESCRIPTION		    "Statically assigned IPv4 address"
	::= { netConfRegisters 2 }


netConfIPv4Mask      OBJECT-TYPE
	SYNTAX				DisplayString
	MAX-ACCESS  		read-write
	STATUS				current
	DESCRIPTION		    "Statically assigned IPv4 subnet mask"
	::= { netConfRegisters 3 }


netConfIPv4Gateway   OBJECT-TYPE
	SYNTAX				DisplayString
	MAX-ACCESS  		read-write
	STATUS				current
	DESCRIPTION		    "Statically assigned IPv4 default gateway"
	::= { netConfRegisters 4 }


netConfPreDNS        OBJECT-TYPE
	SYNTAX				DisplayString
	MAX-ACCESS  		read-write
	STATUS				current
	DESCRIPTION		    "Preferred DNS server"
	::= { netConfRegisters 5 }

netConfAltDNS        OBJECT-TYPE
	SYNTAX				DisplayString
	MAX-ACCESS  		read-write
	STATUS				current
	DESCRIPTION		    "Alternate DNS server"
	::= { netConfRegisters 6 }

netConfDNSTimeout  	OBJECT-TYPE
	SYNTAX				Integer32
	MAX-ACCESS  		read-write
	STATUS				current
	DESCRIPTION		    "Timeout for DNS request in sec"
	::= { netConfRegisters 7}

netConfIPv6Mode  	OBJECT-TYPE
	SYNTAX				INTEGER { autoconf(0), dhcp(1), static(2), disabled(3)}
	MAX-ACCESS  		read-write
	STATUS				current
	DESCRIPTION		    "Method of acquiring IPv6 settings"
	::= { netConfRegisters 8 }


netConfIPv6Addr        OBJECT-TYPE
	SYNTAX				DisplayString
	MAX-ACCESS  		read-write
	STATUS				current
	DESCRIPTION		    "IPv6 Address"
	::= { netConfRegisters 9 }


netConfIPv6Gateway        OBJECT-TYPE
	SYNTAX				DisplayString
	MAX-ACCESS  		read-write
	STATUS				current
	DESCRIPTION		    "IPv6 Default Gateway"
	::= { netConfRegisters 10 }


netConfEnable6to4Tunnel  	OBJECT-TYPE
	SYNTAX				INTEGER { disabled(0), enabled(1)}
	MAX-ACCESS  		read-write
	STATUS				current
	DESCRIPTION		    "Enable ipv6 to ipv4 Tunneling"
	::= { netConfRegisters 11 }

netConfLocalIPAddr        OBJECT-TYPE
	SYNTAX				DisplayString
	MAX-ACCESS  		read-write
	STATUS				current
	DESCRIPTION		    "IPv4 Address of local interface for 6to4 tunnel"
	::= { netConfRegisters 12 }


netConfRemoteIPv4Addr    OBJECT-TYPE
	SYNTAX					DisplayString
	MAX-ACCESS  			read-write
	STATUS					current
	DESCRIPTION				"IPv4 Address of Remote interface for 6to4 tunnel"
	::= { netConfRegisters 13 }


netConfVlanEnabled  	OBJECT-TYPE
	SYNTAX				INTEGER { disabled(0), enabled(1)}
	MAX-ACCESS  		read-write
	STATUS				current
	DESCRIPTION		    "Enable 802.1Q VLAN. Warning: Disables Regular LAN"
	::= { netConfRegisters 14 }

netConfVlanID  		OBJECT-TYPE
	SYNTAX				Integer32
	MAX-ACCESS  		read-write
	STATUS				current
	DESCRIPTION		    "VLAN ID of Tagged Packets (0-4095)"
	::= { netConfRegisters 15}

netConfSave			OBJECT-TYPE
	SYNTAX				INTEGER { normal(0), save(1)}
	MAX-ACCESS  		read-write
	STATUS				current
	DESCRIPTION		    "To Save Network Parameters: Must be set if there is any change of parameters"
	::= { netConfRegisters 16 }

netConfEnableSecurity	OBJECT-TYPE
	SYNTAX				INTEGER { disable(0), enable(1)}
	MAX-ACCESS  		read-write
	STATUS				current
	DESCRIPTION		    "Enable Network Security"
	::= { netConfRegisters 17 }

-- Trap Definitions
intSensorsTraps         OBJECT IDENTIFIER ::= { envTraps 3 }
auxSensorsTraps         OBJECT IDENTIFIER ::= { envTraps 4 }
extSensorsTraps         OBJECT IDENTIFIER ::= { envTraps 5 }
digInputsTraps          OBJECT IDENTIFIER ::= { envTraps 6 }
ipDevicesTraps          OBJECT IDENTIFIER ::= { envTraps 7 }
outRelaysTraps          OBJECT IDENTIFIER ::= { envTraps 8 }
remoteInputsTraps       OBJECT IDENTIFIER ::= { envTraps 12 }
remoteRelaysTraps       OBJECT IDENTIFIER ::= { envTraps 13 }
smokeDetectorsTraps     OBJECT IDENTIFIER ::= { envTraps 14 }
aux2SensorsTraps        OBJECT IDENTIFIER ::= { envTraps 17 }
eventsTraps             OBJECT IDENTIFIER ::= { envTraps 10 }
allExternalSensorsTraps OBJECT IDENTIFIER ::= { envTraps 21 }

envTrapDescription      OBJECT-TYPE
	SYNTAX				DisplayString
	MAX-ACCESS  		read-only
	STATUS				current
	DESCRIPTION	        "Message issued together with the trap to explain the reason the trap was sent"
	::= { envTraps 100 }

envTrapValue            OBJECT-TYPE
	SYNTAX				Integer32 (-1000..1000)
	MAX-ACCESS  		read-only
	STATUS				current
	DESCRIPTION	        "Message issued together with the trap to retrieve a value"
	::= { envTraps 101 }

-- sensor traps
    
-- Internal sensors traps
    
intSensor1Trap          NOTIFICATION-TYPE
    OBJECTS             { envTrapDescription, intSensorIndex, intSensorDescription, intSensorValue, intSensorUnitName, intSensorStatus }
    STATUS              current
    DESCRIPTION         "Trap issued when internal sensor 1 has a notification to send"
    ::= {intSensorsTraps 0 1 }


-- External sensors traps
    
extSensor1Trap          NOTIFICATION-TYPE
    OBJECTS             { envTrapDescription, extSensorIndex, extSensorDescription, extSensorValue, extSensorUnitName, extSensorStatus }
    STATUS              current
    DESCRIPTION         "Trap issued when external sensor 1 (Connector #1) has a notification to send"
    ::= {extSensorsTraps 0 1 }

extSensor2Trap          NOTIFICATION-TYPE
    OBJECTS             { envTrapDescription, extSensorIndex, extSensorDescription, extSensorValue, extSensorUnitName, extSensorStatus }
    STATUS              current
    DESCRIPTION         "Trap issued when external sensor 2 (Connector #1) has a notification to send"
    ::= {extSensorsTraps 0 2 }

extSensor3Trap          NOTIFICATION-TYPE
    OBJECTS             { envTrapDescription, extSensorIndex, extSensorDescription, extSensorValue, extSensorUnitName, extSensorStatus }
    STATUS              current
    DESCRIPTION         "Trap issued when external sensor 3 (Connector #2) has a notification to send"
    ::= {extSensorsTraps 0 3 }

extSensor4Trap          NOTIFICATION-TYPE
    OBJECTS             { envTrapDescription, extSensorIndex, extSensorDescription, extSensorValue, extSensorUnitName, extSensorStatus }
    STATUS              current
    DESCRIPTION         "Trap issued when external sensor 4 (Connector #2) has a notification to send"
    ::= {extSensorsTraps 0 4 }


-- Dry contacts traps
    
digInput1Trap         NOTIFICATION-TYPE
    OBJECTS             { envTrapDescription, digInputIndex, digInputDescription, digInputValue, digInputStatus }
    STATUS              current
    DESCRIPTION         "Trap issued when dry contact 1 (Connector #1) has a notification to send"
    ::= {digInputsTraps 0 1 }

digInput2Trap         NOTIFICATION-TYPE
    OBJECTS             { envTrapDescription, digInputIndex, digInputDescription, digInputValue, digInputStatus }
    STATUS              current
    DESCRIPTION         "Trap issued when dry contact 2 (Connector #2) has a notification to send"
    ::= {digInputsTraps 0 2 }

digInput3Trap         NOTIFICATION-TYPE
    OBJECTS             { envTrapDescription, digInputIndex, digInputDescription, digInputValue, digInputStatus }
    STATUS              current
    DESCRIPTION         "Trap issued when dry contact 3 (Connector #3) has a notification to send"
    ::= {digInputsTraps 0 3 }

digInput4Trap         NOTIFICATION-TYPE
    OBJECTS             { envTrapDescription, digInputIndex, digInputDescription, digInputValue, digInputStatus }
    STATUS              current
    DESCRIPTION         "Trap issued when dry contact 4 (Connector #4) has a notification to send"
    ::= {digInputsTraps 0 4 }

digInput5Trap         NOTIFICATION-TYPE
    OBJECTS             { envTrapDescription, digInputIndex, digInputDescription, digInputValue, digInputStatus }
    STATUS              current
    DESCRIPTION         "Trap issued when dry contact 5 (Connector #5) has a notification to send"
    ::= {digInputsTraps 0 5 }

-- IP Devices traps

ipDevice1Trap           NOTIFICATION-TYPE    
    OBJECTS             { envTrapDescription, ipDeviceIndex, ipDeviceAddress, ipDeviceDescription, ipDeviceValue, ipDeviceStatus }
    STATUS              current
    DESCRIPTION         "Trap issued when IP device #1 has a notification to send"
    ::= { ipDevicesTraps 0 1 }

ipDevice2Trap           NOTIFICATION-TYPE    
    OBJECTS             { envTrapDescription, ipDeviceIndex, ipDeviceAddress, ipDeviceDescription, ipDeviceValue, ipDeviceStatus }
    STATUS              current
    DESCRIPTION         "Trap issued when IP device #2 has a notification to send"
    ::= { ipDevicesTraps 0 2 }

ipDevice3Trap           NOTIFICATION-TYPE    
    OBJECTS             { envTrapDescription, ipDeviceIndex, ipDeviceAddress, ipDeviceDescription, ipDeviceValue, ipDeviceStatus }
    STATUS              current
    DESCRIPTION         "Trap issued when IP device #3 has a notification to send"
    ::= { ipDevicesTraps 0 3 }

ipDevice4Trap           NOTIFICATION-TYPE    
    OBJECTS             { envTrapDescription, ipDeviceIndex, ipDeviceAddress, ipDeviceDescription, ipDeviceValue, ipDeviceStatus }
    STATUS              current
    DESCRIPTION         "Trap issued when IP device #4 has a notification to send"
    ::= { ipDevicesTraps 0 4 }

ipDevice5Trap           NOTIFICATION-TYPE    
    OBJECTS             { envTrapDescription, ipDeviceIndex, ipDeviceAddress, ipDeviceDescription, ipDeviceValue, ipDeviceStatus }
    STATUS              current
    DESCRIPTION         "Trap issued when IP device #5 has a notification to send"
    ::= { ipDevicesTraps 0 5 }

ipDevice6Trap           NOTIFICATION-TYPE    
    OBJECTS             { envTrapDescription, ipDeviceIndex, ipDeviceAddress, ipDeviceDescription, ipDeviceValue, ipDeviceStatus }
    STATUS              current
    DESCRIPTION         "Trap issued when IP device #6 has a notification to send"
    ::= { ipDevicesTraps 0 6 }

ipDevice7Trap           NOTIFICATION-TYPE    
    OBJECTS             { envTrapDescription, ipDeviceIndex, ipDeviceAddress, ipDeviceDescription, ipDeviceValue, ipDeviceStatus }
    STATUS              current
    DESCRIPTION         "Trap issued when IP device #7 has a notification to send"
    ::= { ipDevicesTraps 0 7 }

ipDevice8Trap           NOTIFICATION-TYPE    
    OBJECTS             { envTrapDescription, ipDeviceIndex, ipDeviceAddress, ipDeviceDescription, ipDeviceValue, ipDeviceStatus }
    STATUS              current
    DESCRIPTION         "Trap issued when IP device #8 has a notification to send"
    ::= { ipDevicesTraps 0 8 }

ipDevice9Trap           NOTIFICATION-TYPE    
    OBJECTS             { envTrapDescription, ipDeviceIndex, ipDeviceAddress, ipDeviceDescription, ipDeviceValue, ipDeviceStatus }
    STATUS              current
    DESCRIPTION         "Trap issued when IP device #9 has a notification to send"
    ::= { ipDevicesTraps 0 9 }

ipDevice10Trap          NOTIFICATION-TYPE    
    OBJECTS             { envTrapDescription, ipDeviceIndex, ipDeviceAddress, ipDeviceDescription, ipDeviceValue, ipDeviceStatus }
    STATUS              current
    DESCRIPTION         "Trap issued when IP device #10 has a notification to send"
    ::= { ipDevicesTraps 0 10 }

ipDevice11Trap          NOTIFICATION-TYPE    
    OBJECTS             { envTrapDescription, ipDeviceIndex, ipDeviceAddress, ipDeviceDescription, ipDeviceValue, ipDeviceStatus }
    STATUS              current
    DESCRIPTION         "Trap issued when IP device #11 has a notification to send"
    ::= { ipDevicesTraps 0 11 }

ipDevice12Trap          NOTIFICATION-TYPE    
    OBJECTS             { envTrapDescription, ipDeviceIndex, ipDeviceAddress, ipDeviceDescription, ipDeviceValue, ipDeviceStatus }
    STATUS              current
    DESCRIPTION         "Trap issued when IP device #12 has a notification to send"
    ::= { ipDevicesTraps 0 12 }

ipDevice13Trap          NOTIFICATION-TYPE    
    OBJECTS             { envTrapDescription, ipDeviceIndex, ipDeviceAddress, ipDeviceDescription, ipDeviceValue, ipDeviceStatus }
    STATUS              current
    DESCRIPTION         "Trap issued when IP device #13 has a notification to send"
    ::= { ipDevicesTraps 0 13 }

ipDevice14Trap          NOTIFICATION-TYPE    
    OBJECTS             { envTrapDescription, ipDeviceIndex, ipDeviceAddress, ipDeviceDescription, ipDeviceValue, ipDeviceStatus }
    STATUS              current
    DESCRIPTION         "Trap issued when IP device #14 has a notification to send"
    ::= { ipDevicesTraps 0 14 }

ipDevice15Trap          NOTIFICATION-TYPE    
    OBJECTS             { envTrapDescription, ipDeviceIndex, ipDeviceAddress, ipDeviceDescription, ipDeviceValue, ipDeviceStatus }
    STATUS              current
    DESCRIPTION         "Trap issued when IP device #15 has a notification to send"
    ::= { ipDevicesTraps 0 15 }

ipDevice16Trap          NOTIFICATION-TYPE    
    OBJECTS             { envTrapDescription, ipDeviceIndex, ipDeviceAddress, ipDeviceDescription, ipDeviceValue, ipDeviceStatus }
    STATUS              current
    DESCRIPTION         "Trap issued when IP device #16 has a notification to send"
    ::= { ipDevicesTraps 0 16 }

ipDevice17Trap           NOTIFICATION-TYPE    
    OBJECTS             { envTrapDescription, ipDeviceIndex, ipDeviceAddress, ipDeviceDescription, ipDeviceValue, ipDeviceStatus }
    STATUS              current
    DESCRIPTION         "Trap issued when IP device #17 has a notification to send"
    ::= { ipDevicesTraps 0 17 }

ipDevice18Trap           NOTIFICATION-TYPE    
    OBJECTS             { envTrapDescription, ipDeviceIndex, ipDeviceAddress, ipDeviceDescription, ipDeviceValue, ipDeviceStatus }
    STATUS              current
    DESCRIPTION         "Trap issued when IP device #18 has a notification to send"
    ::= { ipDevicesTraps 0 18 }

ipDevice19Trap           NOTIFICATION-TYPE    
    OBJECTS             { envTrapDescription, ipDeviceIndex, ipDeviceAddress, ipDeviceDescription, ipDeviceValue, ipDeviceStatus }
    STATUS              current
    DESCRIPTION         "Trap issued when IP device #19 has a notification to send"
    ::= { ipDevicesTraps 0 19 }

ipDevice20Trap           NOTIFICATION-TYPE    
    OBJECTS             { envTrapDescription, ipDeviceIndex, ipDeviceAddress, ipDeviceDescription, ipDeviceValue, ipDeviceStatus }
    STATUS              current
    DESCRIPTION         "Trap issued when IP device #20 has a notification to send"
    ::= { ipDevicesTraps 0 20 }

ipDevice21Trap           NOTIFICATION-TYPE    
    OBJECTS             { envTrapDescription, ipDeviceIndex, ipDeviceAddress, ipDeviceDescription, ipDeviceValue, ipDeviceStatus }
    STATUS              current
    DESCRIPTION         "Trap issued when IP device #21 has a notification to send"
    ::= { ipDevicesTraps 0 21 }

ipDevice22Trap           NOTIFICATION-TYPE    
    OBJECTS             { envTrapDescription, ipDeviceIndex, ipDeviceAddress, ipDeviceDescription, ipDeviceValue, ipDeviceStatus }
    STATUS              current
    DESCRIPTION         "Trap issued when IP device #22 has a notification to send"
    ::= { ipDevicesTraps 0 22 }

ipDevice23Trap           NOTIFICATION-TYPE    
    OBJECTS             { envTrapDescription, ipDeviceIndex, ipDeviceAddress, ipDeviceDescription, ipDeviceValue, ipDeviceStatus }
    STATUS              current
    DESCRIPTION         "Trap issued when IP device #23 has a notification to send"
    ::= { ipDevicesTraps 0 23 }

ipDevice24Trap           NOTIFICATION-TYPE    
    OBJECTS             { envTrapDescription, ipDeviceIndex, ipDeviceAddress, ipDeviceDescription, ipDeviceValue, ipDeviceStatus }
    STATUS              current
    DESCRIPTION         "Trap issued when IP device #24 has a notification to send"
    ::= { ipDevicesTraps 0 24 }

ipDevice25Trap           NOTIFICATION-TYPE    
    OBJECTS             { envTrapDescription, ipDeviceIndex, ipDeviceAddress, ipDeviceDescription, ipDeviceValue, ipDeviceStatus }
    STATUS              current
    DESCRIPTION         "Trap issued when IP device #25 has a notification to send"
    ::= { ipDevicesTraps 0 25 }

ipDevice26Trap          NOTIFICATION-TYPE    
    OBJECTS             { envTrapDescription, ipDeviceIndex, ipDeviceAddress, ipDeviceDescription, ipDeviceValue, ipDeviceStatus }
    STATUS              current
    DESCRIPTION         "Trap issued when IP device #26 has a notification to send"
    ::= { ipDevicesTraps 0 26 }

ipDevice27Trap          NOTIFICATION-TYPE    
    OBJECTS             { envTrapDescription, ipDeviceIndex, ipDeviceAddress, ipDeviceDescription, ipDeviceValue, ipDeviceStatus }
    STATUS              current
    DESCRIPTION         "Trap issued when IP device #27 has a notification to send"
    ::= { ipDevicesTraps 0 27 }

ipDevice28Trap          NOTIFICATION-TYPE    
    OBJECTS             { envTrapDescription, ipDeviceIndex, ipDeviceAddress, ipDeviceDescription, ipDeviceValue, ipDeviceStatus }
    STATUS              current
    DESCRIPTION         "Trap issued when IP device #28 has a notification to send"
    ::= { ipDevicesTraps 0 28 }

ipDevice29Trap          NOTIFICATION-TYPE    
    OBJECTS             { envTrapDescription, ipDeviceIndex, ipDeviceAddress, ipDeviceDescription, ipDeviceValue, ipDeviceStatus }
    STATUS              current
    DESCRIPTION         "Trap issued when IP device #29 has a notification to send"
    ::= { ipDevicesTraps 0 29 }

ipDevice30Trap          NOTIFICATION-TYPE    
    OBJECTS             { envTrapDescription, ipDeviceIndex, ipDeviceAddress, ipDeviceDescription, ipDeviceValue, ipDeviceStatus }
    STATUS              current
    DESCRIPTION         "Trap issued when IP device #30 has a notification to send"
    ::= { ipDevicesTraps 0 30 }

ipDevice31Trap          NOTIFICATION-TYPE    
    OBJECTS             { envTrapDescription, ipDeviceIndex, ipDeviceAddress, ipDeviceDescription, ipDeviceValue, ipDeviceStatus }
    STATUS              current
    DESCRIPTION         "Trap issued when IP device #31 has a notification to send"
    ::= { ipDevicesTraps 0 31 }

ipDevice32Trap          NOTIFICATION-TYPE    
    OBJECTS             { envTrapDescription, ipDeviceIndex, ipDeviceAddress, ipDeviceDescription, ipDeviceValue, ipDeviceStatus }
    STATUS              current
    DESCRIPTION         "Trap issued when IP device #32 has a notification to send"
    ::= { ipDevicesTraps 0 32 }

ipDevice33Trap           NOTIFICATION-TYPE    
    OBJECTS             { envTrapDescription, ipDeviceIndex, ipDeviceAddress, ipDeviceDescription, ipDeviceValue, ipDeviceStatus }
    STATUS              current
    DESCRIPTION         "Trap issued when IP device #33 has a notification to send"
    ::= { ipDevicesTraps 0 33 }

ipDevice34Trap           NOTIFICATION-TYPE    
    OBJECTS             { envTrapDescription, ipDeviceIndex, ipDeviceAddress, ipDeviceDescription, ipDeviceValue, ipDeviceStatus }
    STATUS              current
    DESCRIPTION         "Trap issued when IP device #34 has a notification to send"
    ::= { ipDevicesTraps 0 34 }

ipDevice35Trap           NOTIFICATION-TYPE    
    OBJECTS             { envTrapDescription, ipDeviceIndex, ipDeviceAddress, ipDeviceDescription, ipDeviceValue, ipDeviceStatus }
    STATUS              current
    DESCRIPTION         "Trap issued when IP device #35 has a notification to send"
    ::= { ipDevicesTraps 0 35 }

ipDevice36Trap           NOTIFICATION-TYPE    
    OBJECTS             { envTrapDescription, ipDeviceIndex, ipDeviceAddress, ipDeviceDescription, ipDeviceValue, ipDeviceStatus }
    STATUS              current
    DESCRIPTION         "Trap issued when IP device #36 has a notification to send"
    ::= { ipDevicesTraps 0 36 }

ipDevice37Trap           NOTIFICATION-TYPE    
    OBJECTS             { envTrapDescription, ipDeviceIndex, ipDeviceAddress, ipDeviceDescription, ipDeviceValue, ipDeviceStatus }
    STATUS              current
    DESCRIPTION         "Trap issued when IP device #37 has a notification to send"
    ::= { ipDevicesTraps 0 37 }

ipDevice38Trap           NOTIFICATION-TYPE    
    OBJECTS             { envTrapDescription, ipDeviceIndex, ipDeviceAddress, ipDeviceDescription, ipDeviceValue, ipDeviceStatus }
    STATUS              current
    DESCRIPTION         "Trap issued when IP device #38 has a notification to send"
    ::= { ipDevicesTraps 0 38 }

ipDevice39Trap           NOTIFICATION-TYPE    
    OBJECTS             { envTrapDescription, ipDeviceIndex, ipDeviceAddress, ipDeviceDescription, ipDeviceValue, ipDeviceStatus }
    STATUS              current
    DESCRIPTION         "Trap issued when IP device #39 has a notification to send"
    ::= { ipDevicesTraps 0 39 }

ipDevice40Trap           NOTIFICATION-TYPE    
    OBJECTS             { envTrapDescription, ipDeviceIndex, ipDeviceAddress, ipDeviceDescription, ipDeviceValue, ipDeviceStatus }
    STATUS              current
    DESCRIPTION         "Trap issued when IP device #40 has a notification to send"
    ::= { ipDevicesTraps 0 40 }

ipDevice41Trap           NOTIFICATION-TYPE    
    OBJECTS             { envTrapDescription, ipDeviceIndex, ipDeviceAddress, ipDeviceDescription, ipDeviceValue, ipDeviceStatus }
    STATUS              current
    DESCRIPTION         "Trap issued when IP device #41 has a notification to send"
    ::= { ipDevicesTraps 0 41 }

ipDevice42Trap          NOTIFICATION-TYPE    
    OBJECTS             { envTrapDescription, ipDeviceIndex, ipDeviceAddress, ipDeviceDescription, ipDeviceValue, ipDeviceStatus }
    STATUS              current
    DESCRIPTION         "Trap issued when IP device #42 has a notification to send"
    ::= { ipDevicesTraps 0 42 }

ipDevice43Trap          NOTIFICATION-TYPE    
    OBJECTS             { envTrapDescription, ipDeviceIndex, ipDeviceAddress, ipDeviceDescription, ipDeviceValue, ipDeviceStatus }
    STATUS              current
    DESCRIPTION         "Trap issued when IP device #43 has a notification to send"
    ::= { ipDevicesTraps 0 43 }

ipDevice44Trap          NOTIFICATION-TYPE    
    OBJECTS             { envTrapDescription, ipDeviceIndex, ipDeviceAddress, ipDeviceDescription, ipDeviceValue, ipDeviceStatus }
    STATUS              current
    DESCRIPTION         "Trap issued when IP device #44 has a notification to send"
    ::= { ipDevicesTraps 0 44 }

ipDevice45Trap          NOTIFICATION-TYPE    
    OBJECTS             { envTrapDescription, ipDeviceIndex, ipDeviceAddress, ipDeviceDescription, ipDeviceValue, ipDeviceStatus }
    STATUS              current
    DESCRIPTION         "Trap issued when IP device #45 has a notification to send"
    ::= { ipDevicesTraps 0 45 }

ipDevice46Trap          NOTIFICATION-TYPE    
    OBJECTS             { envTrapDescription, ipDeviceIndex, ipDeviceAddress, ipDeviceDescription, ipDeviceValue, ipDeviceStatus }
    STATUS              current
    DESCRIPTION         "Trap issued when IP device #46 has a notification to send"
    ::= { ipDevicesTraps 0 46 }

ipDevice47Trap          NOTIFICATION-TYPE    
    OBJECTS             { envTrapDescription, ipDeviceIndex, ipDeviceAddress, ipDeviceDescription, ipDeviceValue, ipDeviceStatus }
    STATUS              current
    DESCRIPTION         "Trap issued when IP device #47 has a notification to send"
    ::= { ipDevicesTraps 0 47 }

ipDevice48Trap          NOTIFICATION-TYPE    
    OBJECTS             { envTrapDescription, ipDeviceIndex, ipDeviceAddress, ipDeviceDescription, ipDeviceValue, ipDeviceStatus }
    STATUS              current
    DESCRIPTION         "Trap issued when IP device #48 has a notification to send"
    ::= { ipDevicesTraps 0 48 }

ipDevice49Trap           NOTIFICATION-TYPE    
    OBJECTS             { envTrapDescription, ipDeviceIndex, ipDeviceAddress, ipDeviceDescription, ipDeviceValue, ipDeviceStatus }
    STATUS              current
    DESCRIPTION         "Trap issued when IP device #49 has a notification to send"
    ::= { ipDevicesTraps 0 49 }

ipDevice50Trap           NOTIFICATION-TYPE    
    OBJECTS             { envTrapDescription, ipDeviceIndex, ipDeviceAddress, ipDeviceDescription, ipDeviceValue, ipDeviceStatus }
    STATUS              current
    DESCRIPTION         "Trap issued when IP device #50 has a notification to send"
    ::= { ipDevicesTraps 0 50 }

ipDevice51Trap           NOTIFICATION-TYPE    
    OBJECTS             { envTrapDescription, ipDeviceIndex, ipDeviceAddress, ipDeviceDescription, ipDeviceValue, ipDeviceStatus }
    STATUS              current
    DESCRIPTION         "Trap issued when IP device #51 has a notification to send"
    ::= { ipDevicesTraps 0 51 }

ipDevice52Trap           NOTIFICATION-TYPE    
    OBJECTS             { envTrapDescription, ipDeviceIndex, ipDeviceAddress, ipDeviceDescription, ipDeviceValue, ipDeviceStatus }
    STATUS              current
    DESCRIPTION         "Trap issued when IP device #52 has a notification to send"
    ::= { ipDevicesTraps 0 52 }

ipDevice53Trap           NOTIFICATION-TYPE    
    OBJECTS             { envTrapDescription, ipDeviceIndex, ipDeviceAddress, ipDeviceDescription, ipDeviceValue, ipDeviceStatus }
    STATUS              current
    DESCRIPTION         "Trap issued when IP device #53 has a notification to send"
    ::= { ipDevicesTraps 0 53 }

ipDevice54Trap           NOTIFICATION-TYPE    
    OBJECTS             { envTrapDescription, ipDeviceIndex, ipDeviceAddress, ipDeviceDescription, ipDeviceValue, ipDeviceStatus }
    STATUS              current
    DESCRIPTION         "Trap issued when IP device #54 has a notification to send"
    ::= { ipDevicesTraps 0 54 }

ipDevice55Trap           NOTIFICATION-TYPE    
    OBJECTS             { envTrapDescription, ipDeviceIndex, ipDeviceAddress, ipDeviceDescription, ipDeviceValue, ipDeviceStatus }
    STATUS              current
    DESCRIPTION         "Trap issued when IP device #55 has a notification to send"
    ::= { ipDevicesTraps 0 55 }

ipDevice56Trap           NOTIFICATION-TYPE    
    OBJECTS             { envTrapDescription, ipDeviceIndex, ipDeviceAddress, ipDeviceDescription, ipDeviceValue, ipDeviceStatus }
    STATUS              current
    DESCRIPTION         "Trap issued when IP device #56 has a notification to send"
    ::= { ipDevicesTraps 0 56 }

ipDevice57Trap           NOTIFICATION-TYPE    
    OBJECTS             { envTrapDescription, ipDeviceIndex, ipDeviceAddress, ipDeviceDescription, ipDeviceValue, ipDeviceStatus }
    STATUS              current
    DESCRIPTION         "Trap issued when IP device #57 has a notification to send"
    ::= { ipDevicesTraps 0 57 }

ipDevice58Trap          NOTIFICATION-TYPE    
    OBJECTS             { envTrapDescription, ipDeviceIndex, ipDeviceAddress, ipDeviceDescription, ipDeviceValue, ipDeviceStatus }
    STATUS              current
    DESCRIPTION         "Trap issued when IP device #58 has a notification to send"
    ::= { ipDevicesTraps 0 58 }

ipDevice59Trap          NOTIFICATION-TYPE    
    OBJECTS             { envTrapDescription, ipDeviceIndex, ipDeviceAddress, ipDeviceDescription, ipDeviceValue, ipDeviceStatus }
    STATUS              current
    DESCRIPTION         "Trap issued when IP device #59 has a notification to send"
    ::= { ipDevicesTraps 0 59 }

ipDevice60Trap          NOTIFICATION-TYPE    
    OBJECTS             { envTrapDescription, ipDeviceIndex, ipDeviceAddress, ipDeviceDescription, ipDeviceValue, ipDeviceStatus }
    STATUS              current
    DESCRIPTION         "Trap issued when IP device #60 has a notification to send"
    ::= { ipDevicesTraps 0 60 }

ipDevice61Trap          NOTIFICATION-TYPE    
    OBJECTS             { envTrapDescription, ipDeviceIndex, ipDeviceAddress, ipDeviceDescription, ipDeviceValue, ipDeviceStatus }
    STATUS              current
    DESCRIPTION         "Trap issued when IP device #61 has a notification to send"
    ::= { ipDevicesTraps 0 61 }

ipDevice62Trap          NOTIFICATION-TYPE    
    OBJECTS             { envTrapDescription, ipDeviceIndex, ipDeviceAddress, ipDeviceDescription, ipDeviceValue, ipDeviceStatus }
    STATUS              current
    DESCRIPTION         "Trap issued when IP device #62 has a notification to send"
    ::= { ipDevicesTraps 0 62 }

ipDevice63Trap          NOTIFICATION-TYPE    
    OBJECTS             { envTrapDescription, ipDeviceIndex, ipDeviceAddress, ipDeviceDescription, ipDeviceValue, ipDeviceStatus }
    STATUS              current
    DESCRIPTION         "Trap issued when IP device #63 has a notification to send"
    ::= { ipDevicesTraps 0 63 }

ipDevice64Trap          NOTIFICATION-TYPE    
    OBJECTS             { envTrapDescription, ipDeviceIndex, ipDeviceAddress, ipDeviceDescription, ipDeviceValue, ipDeviceStatus }
    STATUS              current
    DESCRIPTION         "Trap issued when IP device #64 has a notification to send"
    ::= { ipDevicesTraps 0 64 }

-- Output Relay trap

outRelay1Trap           NOTIFICATION-TYPE
    OBJECTS             { envTrapDescription, outRelayIndex, outRelayDescription, outRelayStatus }
    STATUS              current
    DESCRIPTION         "Trap issued when output relay changes it's status"
    ::= { outRelaysTraps 0 1 }
    
-- Event Log file trap

evLogFileTrap           NOTIFICATION-TYPE
    OBJECTS             { envTrapDescription }
    STATUS              current
    DESCRIPTION         "Trap issued when the system has an event log file notification to send"
    ::= { envTraps 0 10 }

-- Data Log file trap

dataLogFileTrap         NOTIFICATION-TYPE
    OBJECTS             { envTrapDescription }
    STATUS              current
    DESCRIPTION         "Trap issued when the system has a data log file notification to send (file almost full)"
    ::= { envTraps 0 11 }

remoteDataLogFileTrap   NOTIFICATION-TYPE
    OBJECTS             { envTrapDescription, envTrapValue }
    STATUS              current
    DESCRIPTION         "Trap issued when the system has a data log file reading to send"
    ::= { envTraps 0 12 }
    
-- Smoke Detectors
smokeDetector1Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 1 }
    
smokeDetector2Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 2 }
    
smokeDetector3Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 3 }
    
smokeDetector4Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 4 }
    
smokeDetector5Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 5 }
    
smokeDetector6Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 6 }
    
smokeDetector7Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 7 }
    
smokeDetector8Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 8 }

--remote Input traps

remoteInput1Trap         NOTIFICATION-TYPE
    OBJECTS             { envTrapDescription, remoteInputIndex, remoteInputDescription, remoteInputValue, remoteInputStatus }
    STATUS              current    DESCRIPTION         "Trap issued when remote digital input 1 has a notification to send"
    ::= {remoteInputsTraps 0 1 }

remoteInput2Trap         NOTIFICATION-TYPE
    OBJECTS             { envTrapDescription, remoteInputIndex, remoteInputDescription, remoteInputValue, remoteInputStatus }
    STATUS              current    DESCRIPTION         "Trap issued when remote digital input 2 has a notification to send"
    ::= {remoteInputsTraps 0 2 }

remoteInput3Trap         NOTIFICATION-TYPE
    OBJECTS             { envTrapDescription, remoteInputIndex, remoteInputDescription, remoteInputValue, remoteInputStatus }
    STATUS              current    DESCRIPTION         "Trap issued when remote digital input 3 has a notification to send"
    ::= {remoteInputsTraps 0 3 }

remoteInput4Trap         NOTIFICATION-TYPE
    OBJECTS             { envTrapDescription, remoteInputIndex, remoteInputDescription, remoteInputValue, remoteInputStatus }
    STATUS              current    DESCRIPTION         "Trap issued when remote digital input 4 has a notification to send"
    ::= {remoteInputsTraps 0 4 }

remoteInput5Trap         NOTIFICATION-TYPE
    OBJECTS             { envTrapDescription, remoteInputIndex, remoteInputDescription, remoteInputValue, remoteInputStatus }
    STATUS              current    DESCRIPTION         "Trap issued when remote digital input 5 has a notification to send"
    ::= {remoteInputsTraps 0 5 }

remoteInput6Trap         NOTIFICATION-TYPE
    OBJECTS             { envTrapDescription, remoteInputIndex, remoteInputDescription, remoteInputValue, remoteInputStatus }
    STATUS              current    DESCRIPTION         "Trap issued when remote digital input 6 has a notification to send"
    ::= {remoteInputsTraps 0 6 }

remoteInput7Trap         NOTIFICATION-TYPE
    OBJECTS             { envTrapDescription, remoteInputIndex, remoteInputDescription, remoteInputValue, remoteInputStatus }
    STATUS              current    DESCRIPTION         "Trap issued when remote digital input 7 has a notification to send"
    ::= {remoteInputsTraps 0 7 }

remoteInput8Trap         NOTIFICATION-TYPE
    OBJECTS             { envTrapDescription, remoteInputIndex, remoteInputDescription, remoteInputValue, remoteInputStatus }
    STATUS              current    DESCRIPTION         "Trap issued when remote digital input 8 has a notification to send"
    ::= {remoteInputsTraps 0 8 }

remoteInput9Trap         NOTIFICATION-TYPE
    OBJECTS             { envTrapDescription, remoteInputIndex, remoteInputDescription, remoteInputValue, remoteInputStatus }
    STATUS              current    DESCRIPTION         "Trap issued when remote digital input 9 has a notification to send"
    ::= {remoteInputsTraps 0 9 }

remoteInput10Trap         NOTIFICATION-TYPE
    OBJECTS             { envTrapDescription, remoteInputIndex, remoteInputDescription, remoteInputValue, remoteInputStatus }
    STATUS              current    DESCRIPTION         "Trap issued when remote digital input 10 has a notification to send"
    ::= {remoteInputsTraps 0 10 }

remoteInput11Trap         NOTIFICATION-TYPE
    OBJECTS             { envTrapDescription, remoteInputIndex, remoteInputDescription, remoteInputValue, remoteInputStatus }
    STATUS              current    DESCRIPTION         "Trap issued when remote digital input 11 has a notification to send"
    ::= {remoteInputsTraps 0 11 }

remoteInput12Trap         NOTIFICATION-TYPE
    OBJECTS             { envTrapDescription, remoteInputIndex, remoteInputDescription, remoteInputValue, remoteInputStatus }
    STATUS              current    DESCRIPTION         "Trap issued when remote digital input 12 has a notification to send"
    ::= {remoteInputsTraps 0 12 }

remoteInput13Trap         NOTIFICATION-TYPE
    OBJECTS             { envTrapDescription, remoteInputIndex, remoteInputDescription, remoteInputValue, remoteInputStatus }
    STATUS              current    DESCRIPTION         "Trap issued when remote digital input 13 has a notification to send"
    ::= {remoteInputsTraps 0 13 }

remoteInput14Trap         NOTIFICATION-TYPE
    OBJECTS             { envTrapDescription, remoteInputIndex, remoteInputDescription, remoteInputValue, remoteInputStatus }
    STATUS              current    DESCRIPTION         "Trap issued when remote digital input 14 has a notification to send"
    ::= {remoteInputsTraps 0 14 }

remoteInput15Trap         NOTIFICATION-TYPE
    OBJECTS             { envTrapDescription, remoteInputIndex, remoteInputDescription, remoteInputValue, remoteInputStatus }
    STATUS              current    DESCRIPTION         "Trap issued when remote digital input 15 has a notification to send"
    ::= {remoteInputsTraps 0 15 }

remoteInput16Trap         NOTIFICATION-TYPE
    OBJECTS             { envTrapDescription, remoteInputIndex, remoteInputDescription, remoteInputValue, remoteInputStatus }
    STATUS              current    DESCRIPTION         "Trap issued when remote digital input 16 has a notification to send"
    ::= {remoteInputsTraps 0 16 }

--remote output relay traps

remoteRelay1Trap         NOTIFICATION-TYPE
    OBJECTS             { envTrapDescription, remoteRelayIndex, remoteRelayDescription, remoteRelayStatus }
    STATUS              current    DESCRIPTION         "Trap issued when remote output relay changes it's status"
    ::= {remoteRelaysTraps 0 1 }

remoteRelay2Trap         NOTIFICATION-TYPE
    OBJECTS             { envTrapDescription, remoteRelayIndex, remoteRelayDescription, remoteRelayStatus }
    STATUS              current    DESCRIPTION         "Trap issued when remote output relay changes it's status"
    ::= {remoteRelaysTraps 0 2 }

remoteRelay3Trap         NOTIFICATION-TYPE
    OBJECTS             { envTrapDescription, remoteRelayIndex, remoteRelayDescription, remoteRelayStatus }
    STATUS              current    DESCRIPTION         "Trap issued when remote output relay changes it's status"
    ::= {remoteRelaysTraps 0 3 }

remoteRelay4Trap         NOTIFICATION-TYPE
    OBJECTS             { envTrapDescription, remoteRelayIndex, remoteRelayDescription, remoteRelayStatus }
    STATUS              current    DESCRIPTION         "Trap issued when remote output relay changes it's status"
    ::= {remoteRelaysTraps 0 4 }

remoteRelay5Trap         NOTIFICATION-TYPE
    OBJECTS             { envTrapDescription, remoteRelayIndex, remoteRelayDescription, remoteRelayStatus }
    STATUS              current    DESCRIPTION         "Trap issued when remote output relay changes it's status"
    ::= {remoteRelaysTraps 0 5 }

remoteRelay6Trap         NOTIFICATION-TYPE
    OBJECTS             { envTrapDescription, remoteRelayIndex, remoteRelayDescription, remoteRelayStatus }
    STATUS              current    DESCRIPTION         "Trap issued when remote output relay changes it's status"
    ::= {remoteRelaysTraps 0 6 }

remoteRelay7Trap         NOTIFICATION-TYPE
    OBJECTS             { envTrapDescription, remoteRelayIndex, remoteRelayDescription, remoteRelayStatus }
    STATUS              current    DESCRIPTION         "Trap issued when remote output relay changes it's status"
    ::= {remoteRelaysTraps 0 7 }

remoteRelay8Trap         NOTIFICATION-TYPE
    OBJECTS             { envTrapDescription, remoteRelayIndex, remoteRelayDescription, remoteRelayStatus }
    STATUS              current    DESCRIPTION         "Trap issued when remote output relay changes it's status"
    ::= {remoteRelaysTraps 0 8 }

remoteRelay9Trap         NOTIFICATION-TYPE
    OBJECTS             { envTrapDescription, remoteRelayIndex, remoteRelayDescription, remoteRelayStatus }
    STATUS              current    DESCRIPTION         "Trap issued when remote output relay changes it's status"
    ::= {remoteRelaysTraps 0 9 }

remoteRelay10Trap         NOTIFICATION-TYPE
    OBJECTS             { envTrapDescription, remoteRelayIndex, remoteRelayDescription, remoteRelayStatus }
    STATUS              current    DESCRIPTION         "Trap issued when remote output relay changes it's status"
    ::= {remoteRelaysTraps 0 10 }

remoteRelay11Trap         NOTIFICATION-TYPE
    OBJECTS             { envTrapDescription, remoteRelayIndex, remoteRelayDescription, remoteRelayStatus }
    STATUS              current    DESCRIPTION         "Trap issued when remote output relay changes it's status"
    ::= {remoteRelaysTraps 0 11 }

remoteRelay12Trap         NOTIFICATION-TYPE
    OBJECTS             { envTrapDescription, remoteRelayIndex, remoteRelayDescription, remoteRelayStatus }
    STATUS              current    DESCRIPTION         "Trap issued when remote output relay changes it's status"
    ::= {remoteRelaysTraps 0 12 }

remoteRelay13Trap         NOTIFICATION-TYPE
    OBJECTS             { envTrapDescription, remoteRelayIndex, remoteRelayDescription, remoteRelayStatus }
    STATUS              current    DESCRIPTION         "Trap issued when remote output relay changes it's status"
    ::= {remoteRelaysTraps 0 13 }

remoteRelay14Trap         NOTIFICATION-TYPE
    OBJECTS             { envTrapDescription, remoteRelayIndex, remoteRelayDescription, remoteRelayStatus }
    STATUS              current    DESCRIPTION         "Trap issued when remote output relay changes it's status"
    ::= {remoteRelaysTraps 0 14 }

remoteRelay15Trap         NOTIFICATION-TYPE
    OBJECTS             { envTrapDescription, remoteRelayIndex, remoteRelayDescription, remoteRelayStatus }
    STATUS              current    DESCRIPTION         "Trap issued when remote output relay changes it's status"
    ::= {remoteRelaysTraps 0 15 }

remoteRelay16Trap         NOTIFICATION-TYPE
    OBJECTS             { envTrapDescription, remoteRelayIndex, remoteRelayDescription, remoteRelayStatus }
    STATUS              current    DESCRIPTION         "Trap issued when remote output relay changes it's status"
    ::= {remoteRelaysTraps 0 16 }


event1Trap         NOTIFICATION-TYPE
    OBJECTS             { envTrapDescription, eventIndex, eventDescription, eventStatus, eventValue}
    STATUS              current    DESCRIPTION         "Trap issued when event changes it's status"
    ::= {eventsTraps 0 1 }

event2Trap         NOTIFICATION-TYPE
    OBJECTS             { envTrapDescription, eventIndex, eventDescription, eventStatus, eventValue}
    STATUS              current    DESCRIPTION         "Trap issued when event changes it's status"
    ::= {eventsTraps 0 2 }

event3Trap         NOTIFICATION-TYPE
    OBJECTS            { envTrapDescription, eventIndex, eventDescription, eventStatus, eventValue}
    STATUS              current    DESCRIPTION         "Trap issued when event changes it's status"
    ::= {eventsTraps 0 3 }

event4Trap         NOTIFICATION-TYPE
    OBJECTS             { envTrapDescription, eventIndex, eventDescription, eventStatus, eventValue}
    STATUS              current    DESCRIPTION         "Trap issued when event changes it's status"
    ::= {eventsTraps 0 4 }

event5Trap         NOTIFICATION-TYPE
    OBJECTS             { envTrapDescription, eventIndex, eventDescription, eventStatus, eventValue}
    STATUS              current    DESCRIPTION         "Trap issued when event changes it's status"
    ::= {eventsTraps 0 5 }

event6Trap         NOTIFICATION-TYPE
    OBJECTS             { envTrapDescription, eventIndex, eventDescription, eventStatus, eventValue}
    STATUS              current    DESCRIPTION         "Trap issued when event changes it's status"
    ::= {eventsTraps 0 6 }

event7Trap         NOTIFICATION-TYPE
    OBJECTS            { envTrapDescription, eventIndex, eventDescription, eventStatus, eventValue}
    STATUS              current    DESCRIPTION         "Trap issued when event changes it's status"
    ::= {eventsTraps 0 7 }

event8Trap         NOTIFICATION-TYPE
    OBJECTS             { envTrapDescription, eventIndex, eventDescription, eventStatus, eventValue}
    STATUS              current    DESCRIPTION         "Trap issued when event changes it's status"
    ::= {eventsTraps 0 8}

event9Trap         NOTIFICATION-TYPE
    OBJECTS             { envTrapDescription, eventIndex, eventDescription, eventStatus, eventValue}
    STATUS              current    DESCRIPTION         "Trap issued when event changes it's status"
    ::= {eventsTraps 0 9 }

event10Trap         NOTIFICATION-TYPE
    OBJECTS             { envTrapDescription, eventIndex, eventDescription, eventStatus, eventValue}
    STATUS              current    DESCRIPTION         "Trap issued when event changes it's status"
    ::= {eventsTraps 0 10}


event11Trap         NOTIFICATION-TYPE
    OBJECTS            { envTrapDescription, eventIndex, eventDescription, eventStatus, eventValue}
    STATUS              current    DESCRIPTION         "Trap issued when event changes it's status"
    ::= {eventsTraps 0 11 }

event12Trap         NOTIFICATION-TYPE
    OBJECTS             { envTrapDescription, eventIndex, eventDescription, eventStatus, eventValue}
    STATUS              current    DESCRIPTION         "Trap issued when event changes it's status"
    ::= {eventsTraps 0 12 }

event13Trap         NOTIFICATION-TYPE
    OBJECTS             { envTrapDescription, eventIndex, eventDescription, eventStatus, eventValue}
    STATUS              current    DESCRIPTION         "Trap issued when event changes it's status"
    ::= {eventsTraps 0 13 }

event14Trap         NOTIFICATION-TYPE
    OBJECTS            { envTrapDescription, eventIndex, eventDescription, eventStatus, eventValue}
    STATUS              current    DESCRIPTION         "Trap issued when event changes it's status"
    ::= {eventsTraps 0 14 }

event15Trap         NOTIFICATION-TYPE
    OBJECTS            { envTrapDescription, eventIndex, eventDescription, eventStatus, eventValue}
    STATUS              current    DESCRIPTION         "Trap issued when event changes it's status"
    ::= {eventsTraps 0 15 }

event16Trap         NOTIFICATION-TYPE
    OBJECTS             { envTrapDescription, eventIndex, eventDescription, eventStatus, eventValue}
    STATUS              current    DESCRIPTION         "Trap issued when event changes it's status"
    ::= {eventsTraps 0 16 }

event17Trap         NOTIFICATION-TYPE
    OBJECTS             { envTrapDescription, eventIndex, eventDescription, eventStatus, eventValue}
    STATUS              current    DESCRIPTION         "Trap issued when event changes it's status"
    ::= {eventsTraps 0 17 }

event18Trap         NOTIFICATION-TYPE
    OBJECTS            { envTrapDescription, eventIndex, eventDescription, eventStatus, eventValue}
    STATUS              current    DESCRIPTION         "Trap issued when event changes it's status"
    ::= {eventsTraps 0 18}

event19Trap         NOTIFICATION-TYPE
    OBJECTS            { envTrapDescription, eventIndex, eventDescription, eventStatus, eventValue}
    STATUS              current    DESCRIPTION         "Trap issued when event changes it's status"
    ::= {eventsTraps 0 19 }

event20Trap         NOTIFICATION-TYPE
    OBJECTS            { envTrapDescription, eventIndex, eventDescription, eventStatus, eventValue}
    STATUS              current    DESCRIPTION         "Trap issued when event changes it's status"
    ::= {eventsTraps 0 20}


event21Trap         NOTIFICATION-TYPE
    OBJECTS             { envTrapDescription, eventIndex, eventDescription, eventStatus, eventValue}
    STATUS              current    DESCRIPTION         "Trap issued when event changes it's status"
    ::= {eventsTraps 0 21 }

event22Trap         NOTIFICATION-TYPE
    OBJECTS            { envTrapDescription, eventIndex, eventDescription, eventStatus, eventValue}
    STATUS              current    DESCRIPTION         "Trap issued when event changes it's status"
    ::= {eventsTraps 0 22 }

event23Trap         NOTIFICATION-TYPE
    OBJECTS            { envTrapDescription, eventIndex, eventDescription, eventStatus, eventValue}
    STATUS              current    DESCRIPTION         "Trap issued when event changes it's status"
    ::= {eventsTraps 0 23 }

event24Trap         NOTIFICATION-TYPE
    OBJECTS            { envTrapDescription, eventIndex, eventDescription, eventStatus, eventValue}
    STATUS              current    DESCRIPTION         "Trap issued when event changes it's status"
    ::= {eventsTraps 0 24 }

event25Trap         NOTIFICATION-TYPE
    OBJECTS             { envTrapDescription, eventIndex, eventDescription, eventStatus, eventValue}
    STATUS              current    DESCRIPTION         "Trap issued when event changes it's status"
    ::= {eventsTraps 0 25 }

event26Trap         NOTIFICATION-TYPE
    OBJECTS             { envTrapDescription, eventIndex, eventDescription, eventStatus, eventValue}
    STATUS              current    DESCRIPTION         "Trap issued when event changes it's status"
    ::= {eventsTraps 0 26 }

event27Trap         NOTIFICATION-TYPE
    OBJECTS             { envTrapDescription, eventIndex, eventDescription, eventStatus, eventValue}
    STATUS              current    DESCRIPTION         "Trap issued when event changes it's status"
    ::= {eventsTraps 0 27 }

event28Trap         NOTIFICATION-TYPE
    OBJECTS             { envTrapDescription, eventIndex, eventDescription, eventStatus, eventValue}
    STATUS              current    DESCRIPTION         "Trap issued when event changes it's status"
    ::= {eventsTraps 0 28}

event29Trap         NOTIFICATION-TYPE
    OBJECTS            { envTrapDescription, eventIndex, eventDescription, eventStatus, eventValue}
    STATUS              current    DESCRIPTION         "Trap issued when event changes it's status"
    ::= {eventsTraps 0 29 }

event30Trap         NOTIFICATION-TYPE
    OBJECTS             { envTrapDescription, eventIndex, eventDescription, eventStatus, eventValue}
    STATUS              current    DESCRIPTION         "Trap issued when event changes it's status"
    ::= {eventsTraps 0 30}

event31Trap         NOTIFICATION-TYPE
    OBJECTS            { envTrapDescription, eventIndex, eventDescription, eventStatus, eventValue}
    STATUS              current    DESCRIPTION         "Trap issued when event changes it's status"
    ::= {eventsTraps 0 31 }

event32Trap         NOTIFICATION-TYPE
    OBJECTS            { envTrapDescription, eventIndex, eventDescription, eventStatus, eventValue}
    STATUS              current    DESCRIPTION         "Trap issued when event changes it's status"
    ::= {eventsTraps 0 32}


allexternal1Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 1}

allexternal2Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 2}

allexternal3Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 3}

allexternal4Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 4}

allexternal5Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 5}

allexternal6Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 6}

allexternal7Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 7}

allexternal8Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 8}

allexternal9Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 9}

allexternal10Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 10}

allexternal11Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 11}

allexternal12Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 12}

allexternal13Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 13}

allexternal14Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 14}

allexternal15Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 15}

allexternal16Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 16}

allexternal17Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 17}

allexternal18Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 18}

allexternal19Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 19}

allexternal20Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 20}

allexternal21Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 21}

allexternal22Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 22}

allexternal23Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 23}

allexternal24Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 24}

allexternal25Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 25}

allexternal26Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 26}

allexternal27Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 27}

allexternal28Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 28}

allexternal29Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 29}

allexternal30Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 30}

allexternal31Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 31}

allexternal32Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 32}

allexternal33Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 33}

allexternal34Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 34}

allexternal35Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 35}

allexternal36Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 36}

allexternal37Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 37}

allexternal38Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 38}

allexternal39Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 39}

allexternal40Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 40}

allexternal41Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 41}

allexternal42Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 42}

allexternal43Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 43}

allexternal44Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 44}

allexternal45Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 45}

allexternal46Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 46}

allexternal47Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 47}

allexternal48Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 48}

allexternal49Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 49}

allexternal50Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 50}

allexternal51Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 51}

allexternal52Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 52}

allexternal53Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 53}

allexternal54Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 54}

allexternal55Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 55}

allexternal56Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 56}

allexternal57Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 57}

allexternal58Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 58}

allexternal59Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 59}

allexternal60Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 60}

allexternal61Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 61}

allexternal62Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 62}

allexternal63Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 63}

allexternal64Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 64}

allexternal65Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 65}

allexternal66Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 66}

allexternal67Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 67}

allexternal68Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 68}

allexternal69Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 69}

allexternal70Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 70}

allexternal71Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 71}

allexternal72Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 72}

allexternal73Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 73}

allexternal74Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 74}

allexternal75Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 75}

allexternal76Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 76}

allexternal77Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 77}

allexternal78Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 78}

allexternal79Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 79}

allexternal80Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 80}

allexternal81Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 81}

allexternal82Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 82}

allexternal83Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 83}

allexternal84Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 84}

allexternal85Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 85}

allexternal86Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 86}

allexternal87Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 87}

allexternal88Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 88}

allexternal89Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 89}

allexternal90Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 90}

allexternal91Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 91}

allexternal92Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 92}

allexternal93Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 93}

allexternal94Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 94}

allexternal95Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 95}

allexternal96Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 96}

allexternal97Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 97}

allexternal98Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 98}

allexternal99Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 99}

allexternal100Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 100}

allexternal101Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 101}

allexternal102Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 102}

allexternal103Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 103}

allexternal104Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 104}

allexternal105Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 105}

allexternal106Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 106}

allexternal107Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 107}

allexternal108Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 108}

allexternal109Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 109}

allexternal110Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 110}

allexternal111Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 111}

allexternal112Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 112}

allexternal113Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 113}

allexternal114Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 114}

allexternal115Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 115}

allexternal116Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 116}

allexternal117Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 117}

allexternal118Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 118}

allexternal119Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 119}

allexternal120Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 120}

allexternal121Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 121}

allexternal122Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 122}

allexternal123Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 123}

allexternal124Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 124}

allexternal125Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 125}

allexternal126Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 126}

allexternal127Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 127}

allexternal128Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 128}

allexternal129Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 129}

allexternal130Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 130}

allexternal131Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 131}

allexternal132Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 132}

allexternal133Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 133}

allexternal134Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 134}

allexternal135Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 135}

allexternal136Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 136}

allexternal137Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 137}

allexternal138Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 138}

allexternal139Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 139}

allexternal140Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 140}

allexternal141Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 141}

allexternal142Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 142}

allexternal143Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 143}

allexternal144Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 144}

allexternal145Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 145}

allexternal146Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 146}

allexternal147Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 147}

allexternal148Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 148}

allexternal149Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 149}

allexternal150Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 150}

allexternal151Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 151}

allexternal152Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 152}

allexternal153Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 153}

allexternal154Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 154}

allexternal155Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 155}

allexternal156Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 156}

allexternal157Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 157}

allexternal158Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 158}

allexternal159Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 159}

allexternal160Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 160}

allexternal161Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 161}

allexternal162Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 162}

allexternal163Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 163}

allexternal164Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 164}

allexternal165Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 165}

allexternal166Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 166}

allexternal167Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 167}

allexternal168Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 168}

allexternal169Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 169}

allexternal170Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 170}

allexternal171Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 171}

allexternal172Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 172}

allexternal173Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 173}

allexternal174Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 174}

allexternal175Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 175}

allexternal176Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 176}

allexternal177Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 177}

allexternal178Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 178}

allexternal179Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 179}

allexternal180Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 180}

allexternal181Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 181}

allexternal182Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 182}

allexternal183Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 183}

allexternal184Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 184}

allexternal185Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 185}

allexternal186Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 186}

allexternal187Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 187}

allexternal188Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 188}

allexternal189Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 189}

allexternal190Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 190}

allexternal191Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 191}

allexternal192Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 192}

allexternal193Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 193}

allexternal194Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 194}

allexternal195Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 195}

allexternal196Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 196}

allexternal197Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 197}

allexternal198Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 198}

allexternal199Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 199}

allexternal200Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 200}

allexternal201Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 201}

allexternal202Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 202}

allexternal203Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 203}

allexternal204Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 204}

allexternal205Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 205}

allexternal206Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 206}

allexternal207Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 207}

allexternal208Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 208}

allexternal209Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 209}

allexternal210Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 210}

allexternal211Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 211}

allexternal212Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 212}

allexternal213Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 213}

allexternal214Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 214}

allexternal215Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 215}

allexternal216Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 216}

allexternal217Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 217}

allexternal218Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 218}

allexternal219Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 219}

allexternal220Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 220}

allexternal221Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 221}

allexternal222Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 222}

allexternal223Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 223}

allexternal224Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 224}

allexternal225Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 225}

allexternal226Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 226}

allexternal227Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 227}

allexternal228Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 228}

allexternal229Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 229}

allexternal230Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 230}

allexternal231Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 231}

allexternal232Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 232}

allexternal233Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 233}

allexternal234Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 234}

allexternal235Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 235}

allexternal236Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 236}

allexternal237Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 237}

allexternal238Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 238}

allexternal239Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 239}

allexternal240Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 240}

allexternal241Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 241}

allexternal242Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 242}

allexternal243Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 243}

allexternal244Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 244}

allexternal245Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 245}

allexternal246Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 246}

allexternal247Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 247}

allexternal248Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 248}

allexternal249Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 249}

allexternal250Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 250}

allexternal251Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 251}

allexternal252Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 252}

allexternal253Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 253}

allexternal254Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 254}

allexternal255Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 255}

allexternal256Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 256}

allexternal257Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 257}

allexternal258Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 258}

allexternal259Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 259}

allexternal260Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 260}

allexternal261Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 261}

allexternal262Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 262}

allexternal263Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 263}

allexternal264Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 264}

allexternal265Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 265}

allexternal266Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 266}

allexternal267Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 267}

allexternal268Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 268}

allexternal269Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 269}

allexternal270Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 270}

allexternal271Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 271}

allexternal272Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 272}

allexternal273Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 273}

allexternal274Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 274}

allexternal275Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 275}

allexternal276Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 276}

allexternal277Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 277}

allexternal278Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 278}

allexternal279Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 279}

allexternal280Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 280}

allexternal281Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 281}

allexternal282Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 282}

allexternal283Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 283}

allexternal284Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 284}

allexternal285Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 285}

allexternal286Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 286}

allexternal287Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 287}

allexternal288Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 288}

allexternal289Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 289}

allexternal290Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 290}

allexternal291Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 291}

allexternal292Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 292}

allexternal293Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 293}

allexternal294Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 294}

allexternal295Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 295}

allexternal296Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 296}

allexternal297Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 297}

allexternal298Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 298}

allexternal299Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 299}

allexternal300Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 300}

allexternal301Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 301}

allexternal302Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 302}

allexternal303Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 303}

allexternal304Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 304}

allexternal305Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 305}

allexternal306Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 306}

allexternal307Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 307}

allexternal308Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 308}

allexternal309Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 309}

allexternal310Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 310}

allexternal311Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 311}

allexternal312Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 312}

allexternal313Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 313}

allexternal314Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 314}

allexternal315Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 315}

allexternal316Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 316}

allexternal317Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 317}

allexternal318Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 318}

allexternal319Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 319}

allexternal320Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 320}

allexternal321Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 321}

allexternal322Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 322}

allexternal323Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 323}

allexternal324Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 324}

allexternal325Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 325}

allexternal326Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 326}

allexternal327Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 327}

allexternal328Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 328}

allexternal329Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 329}

allexternal330Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 330}

allexternal331Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 331}

allexternal332Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 332}

allexternal333Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 333}

allexternal334Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 334}

allexternal335Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 335}

allexternal336Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 336}

allexternal337Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 337}

allexternal338Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 338}

allexternal339Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 339}

allexternal340Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 340}

allexternal341Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 341}

allexternal342Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 342}

allexternal343Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 343}

allexternal344Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 344}

allexternal345Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 345}

allexternal346Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 346}

allexternal347Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 347}

allexternal348Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 348}

allexternal349Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 349}

allexternal350Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 350}

allexternal351Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 351}

allexternal352Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 352}

allexternal353Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 353}

allexternal354Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 354}

allexternal355Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 355}

allexternal356Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 356}

allexternal357Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 357}

allexternal358Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 358}

allexternal359Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 359}

allexternal360Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 360}

allexternal361Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 361}

allexternal362Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 362}

allexternal363Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 363}

allexternal364Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 364}

allexternal365Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 365}

allexternal366Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 366}

allexternal367Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 367}

allexternal368Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 368}

allexternal369Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 369}

allexternal370Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 370}

allexternal371Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 371}

allexternal372Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 372}

allexternal373Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 373}

allexternal374Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 374}

allexternal375Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 375}

allexternal376Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 376}

allexternal377Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 377}

allexternal378Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 378}

allexternal379Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 379}

allexternal380Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 380}

allexternal381Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 381}

allexternal382Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 382}

allexternal383Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 383}

allexternal384Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 384}

allexternal385Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 385}

allexternal386Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 386}

allexternal387Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 387}

allexternal388Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 388}

allexternal389Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 389}

allexternal390Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 390}

allexternal391Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 391}

allexternal392Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 392}

allexternal393Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 393}

allexternal394Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 394}

allexternal395Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 395}

allexternal396Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 396}

allexternal397Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 397}

allexternal398Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 398}

allexternal399Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 399}

allexternal400Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 400}

allexternal401Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 401}

allexternal402Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 402}

allexternal403Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 403}

allexternal404Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 404}

allexternal405Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 405}

allexternal406Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 406}

allexternal407Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 407}

allexternal408Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 408}

allexternal409Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 409}

allexternal410Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 410}

allexternal411Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 411}

allexternal412Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 412}

allexternal413Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 413}

allexternal414Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 414}

allexternal415Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 415}

allexternal416Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 416}

allexternal417Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 417}

allexternal418Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 418}

allexternal419Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 419}

allexternal420Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 420}

allexternal421Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 421}

allexternal422Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 422}

allexternal423Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 423}

allexternal424Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 424}

allexternal425Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 425}

allexternal426Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 426}

allexternal427Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 427}

allexternal428Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 428}

allexternal429Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 429}

allexternal430Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 430}

allexternal431Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 431}

allexternal432Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 432}

allexternal433Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 433}

allexternal434Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 434}

allexternal435Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 435}

allexternal436Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 436}

allexternal437Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 437}

allexternal438Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 438}

allexternal439Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 439}

allexternal440Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 440}

allexternal441Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 441}

allexternal442Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 442}

allexternal443Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 443}

allexternal444Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 444}

allexternal445Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 445}

allexternal446Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 446}

allexternal447Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 447}

allexternal448Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 448}

allexternal449Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 449}

allexternal450Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 450}

allexternal451Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 451}

allexternal452Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 452}

allexternal453Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 453}

allexternal454Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 454}

allexternal455Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 455}

allexternal456Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 456}

allexternal457Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 457}

allexternal458Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 458}

allexternal459Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 459}

allexternal460Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 460}

allexternal461Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 461}

allexternal462Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 462}

allexternal463Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 463}

allexternal464Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 464}

allexternal465Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 465}

allexternal466Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 466}

allexternal467Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 467}

allexternal468Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 468}

allexternal469Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 469}

allexternal470Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 470}

allexternal471Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 471}

allexternal472Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 472}

allexternal473Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 473}

allexternal474Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 474}

allexternal475Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 475}

allexternal476Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 476}

allexternal477Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 477}

allexternal478Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 478}

allexternal479Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 479}

allexternal480Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 480}

allexternal481Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 481}

allexternal482Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 482}

allexternal483Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 483}

allexternal484Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 484}

allexternal485Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 485}

allexternal486Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 486}

allexternal487Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 487}

allexternal488Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 488}

allexternal489Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 489}

allexternal490Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 490}

allexternal491Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 491}

allexternal492Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 492}

allexternal493Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 493}

allexternal494Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 494}

allexternal495Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 495}

allexternal496Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 496}

allexternal497Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 497}

allexternal498Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 498}

allexternal499Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 499}

allexternal500Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 500}

allexternal501Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 501}

allexternal502Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 502}

allexternal503Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 503}

allexternal504Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 504}

allexternal505Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 505}

allexternal506Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 506}

allexternal507Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 507}

allexternal508Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 508}

allexternal509Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 509}

allexternal510Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 510}

allexternal511Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 511}

allexternal512Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 512}

allexternal513Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 513}

allexternal514Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 514}

allexternal515Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 515}

allexternal516Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 516}

allexternal517Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 517}

allexternal518Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 518}

allexternal519Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 519}

allexternal520Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 520}

allexternal521Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 521}

allexternal522Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 522}

allexternal523Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 523}

allexternal524Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 524}

allexternal525Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 525}

allexternal526Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 526}

allexternal527Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 527}

allexternal528Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 528}

allexternal529Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 529}

allexternal530Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 530}

allexternal531Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 531}

allexternal532Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 532}

allexternal533Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 533}

allexternal534Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 534}

allexternal535Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 535}

allexternal536Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 536}

allexternal537Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 537}

allexternal538Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 538}

allexternal539Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 539}

allexternal540Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 540}

allexternal541Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 541}

allexternal542Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 542}

allexternal543Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 543}

allexternal544Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 544}

allexternal545Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 545}

allexternal546Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 546}

allexternal547Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 547}

allexternal548Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 548}

allexternal549Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 549}

allexternal550Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 550}

allexternal551Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 551}

allexternal552Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 552}

allexternal553Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 553}

allexternal554Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 554}

allexternal555Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 555}

allexternal556Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 556}

allexternal557Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 557}

allexternal558Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 558}

allexternal559Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 559}

allexternal560Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 560}

allexternal561Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 561}

allexternal562Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 562}

allexternal563Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 563}

allexternal564Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 564}

allexternal565Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 565}

allexternal566Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 566}

allexternal567Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 567}

allexternal568Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 568}

allexternal569Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 569}

allexternal570Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 570}

allexternal571Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 571}

allexternal572Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 572}

allexternal573Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 573}

allexternal574Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 574}

allexternal575Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 575}

allexternal576Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 576}

allexternal577Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 577}

allexternal578Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 578}

allexternal579Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 579}

allexternal580Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 580}

allexternal581Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 581}

allexternal582Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 582}

allexternal583Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 583}

allexternal584Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 584}

allexternal585Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 585}

allexternal586Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 586}

allexternal587Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 587}

allexternal588Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 588}

allexternal589Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 589}

allexternal590Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 590}

allexternal591Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 591}

allexternal592Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 592}

allexternal593Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 593}

allexternal594Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 594}

allexternal595Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 595}

allexternal596Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 596}

allexternal597Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 597}

allexternal598Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 598}

allexternal599Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 599}

allexternal600Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 600}

allexternal601Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 601}

allexternal602Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 602}

allexternal603Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 603}

allexternal604Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 604}

allexternal605Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 605}

allexternal606Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 606}

allexternal607Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 607}

allexternal608Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 608}

allexternal609Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 609}

allexternal610Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 610}

allexternal611Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 611}

allexternal612Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 612}

allexternal613Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 613}

allexternal614Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 614}

allexternal615Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 615}

allexternal616Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 616}

allexternal617Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 617}

allexternal618Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 618}

allexternal619Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 619}

allexternal620Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 620}

allexternal621Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 621}

allexternal622Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 622}

allexternal623Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 623}

allexternal624Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 624}

allexternal625Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 625}

allexternal626Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 626}

allexternal627Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 627}

allexternal628Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 628}

allexternal629Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 629}

allexternal630Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 630}

allexternal631Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 631}

allexternal632Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 632}

allexternal633Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 633}

allexternal634Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 634}

allexternal635Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 635}

allexternal636Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 636}

allexternal637Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 637}

allexternal638Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 638}

allexternal639Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 639}

allexternal640Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 640}

allexternal641Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 641}

allexternal642Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 642}

allexternal643Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 643}

allexternal644Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 644}

allexternal645Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 645}

allexternal646Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 646}

allexternal647Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 647}

allexternal648Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 648}

allexternal649Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 649}

allexternal650Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 650}

allexternal651Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 651}

allexternal652Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 652}

allexternal653Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 653}

allexternal654Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 654}

allexternal655Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 655}

allexternal656Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 656}

allexternal657Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 657}

allexternal658Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 658}

allexternal659Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 659}

allexternal660Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 660}

allexternal661Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 661}

allexternal662Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 662}

allexternal663Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 663}

allexternal664Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 664}

allexternal665Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 665}

allexternal666Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 666}

allexternal667Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 667}

allexternal668Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 668}

allexternal669Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 669}

allexternal670Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 670}

allexternal671Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 671}

allexternal672Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 672}

allexternal673Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 673}

allexternal674Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 674}

allexternal675Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 675}

allexternal676Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 676}

allexternal677Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 677}

allexternal678Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 678}

allexternal679Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 679}

allexternal680Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 680}

allexternal681Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 681}

allexternal682Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 682}

allexternal683Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 683}

allexternal684Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 684}

allexternal685Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 685}

allexternal686Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 686}

allexternal687Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 687}

allexternal688Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 688}

allexternal689Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 689}

allexternal690Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 690}

allexternal691Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 691}

allexternal692Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 692}

allexternal693Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 693}

allexternal694Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 694}

allexternal695Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 695}

allexternal696Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 696}

allexternal697Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 697}

allexternal698Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 698}

allexternal699Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 699}

allexternal700Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 700}

allexternal701Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 701}

allexternal702Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 702}

allexternal703Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 703}

allexternal704Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 704}

allexternal705Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 705}

allexternal706Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 706}

allexternal707Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 707}

allexternal708Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 708}

allexternal709Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 709}

allexternal710Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 710}

allexternal711Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 711}

allexternal712Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 712}

allexternal713Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 713}

allexternal714Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 714}

allexternal715Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 715}

allexternal716Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 716}

allexternal717Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 717}

allexternal718Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 718}

allexternal719Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 719}

allexternal720Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 720}

allexternal721Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 721}

allexternal722Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 722}

allexternal723Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 723}

allexternal724Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 724}

allexternal725Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 725}

allexternal726Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 726}

allexternal727Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 727}

allexternal728Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 728}

allexternal729Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 729}

allexternal730Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 730}

allexternal731Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 731}

allexternal732Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 732}

allexternal733Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 733}

allexternal734Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 734}

allexternal735Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 735}

allexternal736Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 736}

allexternal737Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 737}

allexternal738Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 738}

allexternal739Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 739}

allexternal740Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 740}

allexternal741Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 741}

allexternal742Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 742}

allexternal743Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 743}

allexternal744Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 744}

allexternal745Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 745}

allexternal746Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 746}

allexternal747Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 747}

allexternal748Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 748}

allexternal749Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 749}

allexternal750Trap   NOTIFICATION-TYPE
    OBJECTS           { envTrapDescription, allExternalSensorUID, allExternalSensorDescription, allExternalSensorValue, allExternalSensorConnector, allExternalSensorStatus} 
    STATUS              current    DESCRIPTION         "Trap issued when sensor changes it's status" 
    ::= {allExternalSensorsTraps 0 750}






END
